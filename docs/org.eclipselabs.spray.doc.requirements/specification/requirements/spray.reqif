# Spray

# Specification
- name: org.eclipselabs.spray.requirements.issues
- description: This package contains all requirements grabbed in the Spray Google Code issues: http://code.google.com/a/eclipselabs.org/p/spray/issues/list

## issue0001 (FunctionalRequirement)
Patch for /wiki/Spray_DSL_Ideas.wiki
- stakeholder: Spray developer
- keywords: Type: Patch
- status: DONE

## issue0002 (FunctionalRequirement)
There is a path hard coded in JavaGenFile.java.
- stakeholder: Spray developer
- keywords: Priority: Medium, Type: Defect, Component: Code generator
- status: DONE

## issue0003 (FunctionalRequirement)
Downgrade version to 0.1.0
- stakeholder: Spray developer
- keywords: Priority: Medium, Type: Defect, Component: Build
- status: DONE

## issue0004 (FunctionalRequirement)
Add feature projects
- stakeholder: Spray developer
- keywords: Priority: Medium, Type: Task, Component: Build
- status: DONE

## issue0005 (FunctionalRequirement)
Add Maven POMs
- stakeholder: Spray developer
- keywords: Priority: Medium, Type: Task, Component: Build
- status: DONE

## issue0006 (FunctionalRequirement)
Use real cross-references for rule MetaClass
- stakeholder: Diagram editor creator
- keywords: Priority: Medium, Type: Defect, Component: Language, Spray DSL
- status: DONE

## issue0007 (FunctionalRequirement)
Enable referencing of IColorConstant instances as color
- stakeholder: Diagram editor creator
- keywords: Priority: Medium, Type: Defect, Component: Language, Styles DSL
- status: DONE

## issue0008 (FunctionalRequirement)
Provide working SWTBot Tests for the example project
- stakeholder: Spray developer
- keywords: Priority: Medium, Type: Enhancement, Component: Test, Examples
- status: DONE

## issue0009 (FunctionalRequirement)
Derive grammar from Xbase
- stakeholder: Spray developer
- keywords: Priority: Medium, Type: Defect, Component: Language
- status: DONE

## issue0010 (FunctionalRequirement)
Include dependent artifacts into p2-repository
- stakeholder: Spray developer
- keywords: Priority: Medium, Type: Task, Component: Build
- status: DONE

## issue0011 (FunctionalRequirement)
Execute Xtext generator in the build
- stakeholder: Spray developer
- keywords: Priority: Medium, Type: Task, Component: Build
- status: DONE

## issue0012 (FunctionalRequirement)
Change the path handling so the Graphiti generator can be used inside an automated build
- stakeholder: Spray developer
- keywords: Priority: Medium, Type: Defect, Component: Build
- status: DONE

## issue0013 (FunctionalRequirement)
Xtend: use typeof() instead of instanceof in filter
- stakeholder: Spray developer
- keywords: Priority: Medium, Type: Defect, Component: Code generator
- status: DONE

## issue0014 (FunctionalRequirement)
Use @Inject instead of new operator in Xtend
- stakeholder: Spray developer
- keywords: Priority-Medium, Type: Defect, Component: Code generator
- status: DONE

## issue0015 (FunctionalRequirement)
Make generation of timestamps configurable in properties file
- stakeholder: Diagram editor creator
- keywords: Priority: Medium, Type: Enhancement, Component: Code generator, Properties file
- status: DONE

## issue0016 (FunctionalRequirement)
Trigger generator on changing the properties file
- stakeholder: Diagram editor creator
- keywords: Priority: Medium, Type: Enhancement, Component: Code generator, Properties file
- status: DONE

## issue0017 (FunctionalRequirement)
Integrate JDT Formatter
- stakeholder: Diagram editor creator
- keywords: Priority: Medium, Type: Enhancement
- status: DONE

## issue0018 (FunctionalRequirement)
Task: Generate org.xspray.mm classes in the build process
- stakeholder: Spray developer
- keywords: Type: Task
- status: DONE

## issue0019 (QualityRequirement)
Installation instructions
- stakeholder: Diagram editor creator
- keywords: Priority: Medium, Type: Defect, Component: Documentation
- status: DONE

## issue0020 (FunctionalRequirement)
Missing package in example from CI build
- stakeholder: Spray developer
- keywords: Priority: Medium, Type: Defect, Component: Build
- status: DONE

## issue0021 (FunctionalRequirement)
Provide Xspray new project wizard
- stakeholder: Diagram editor creator
- keywords: Priority: Medium, Type: Enhancement, Spray project wizard
- status: DONE

## issue0022 (FunctionalRequirement)
The generation gap classes are placed in src-gen, should be placed in src
- stakeholder: Diagram editor creator
- keywords: Priority: Medium, Type: Defect, Component: Code generator
- status: DONE

## issue0023 (FunctionalRequirement)
DSL and generator does not support defining figures containing images
Duplicate of issue0121
- keywords: Priority: Medium, Type: Enhancement
- status: DONE

## issue0024 (FunctionalRequirement)
Provide Spray diagram wizard
- stakeholder: Diagram editor user
- keywords: Priority: Low, Type: Enhancement, Component: Code generator, Spray project wizard
- status: DONE

## issue0025 (FunctionalRequirement)
Could not build Xspray locally
- stakeholder: Spray developer
- keywords: Priority: Medium, Type: Defect, Component: Build
- status: DONE

## issue0026 (FunctionalRequirement)
MWE2 UI not installed in Spray SDK
- stakeholder: Spray developer
- keywords: Priority: Medium, Type: Defect, Component: Build
- status: DONE

## issue0027 (FunctionalRequirement)
Rename projects to prefix org.eclipselabs.spray
- stakeholder: Spray developer
- keywords: Type: Task, Component: Build
- status: DONE

## issue0028 (FunctionalRequirement)
Add feature/plugin properties
- stakeholder: Spray developer
- keywords: Type: Task, Component: Build
- status: DONE

## issue0029 (FunctionalRequirement)
Add content assist for Icons
- stakeholder: Diagram editor creator
- keywords: Priority: Medium, Type: Enhancement, Component: UI, Usability
- status: DONE

## issue0030 (FunctionalRequirement)
Generated class names should start with capital letter
- stakeholder: Spray developer
- keywords: Priority: Medium, Type: Defect, Component: Code generator
- status: DONE

## issue0031 (FunctionalRequirement)
Use ImportUtil to manage imports in templates
- stakeholder: Spray developer
- keywords: Priority: Medium, Type: Defect, Component: Code generator
- status: DONE

## issue0032 (FunctionalRequirement)
Cannot open generated diagram editor
- stakeholder: Diagram editor creator
- keywords: Priority: High, Type: Defect, Component: UI
- status: DONE

## issue0033 (FunctionalRequirement)
Move complete generator logic to o.e.s.generator.graphiti
- stakeholder: Spray developer
- keywords: Priority: Medium, Type: Defect, Component: Code generator
- status: DONE

## issue0034 (FunctionalRequirement)
Allow user defined RGB color values
- stakeholder: Diagram editor creator
- keywords: Priority: Medium, Type: Enhancement, Component: Language, Styles DSL
- status: DONE

## issue0035 (QualityRequirement)
Remove dependencies to Graphiti plugins from DSL plugins
The o.e.s.xtext.ui plugin has dependencies to the Spray Graphiti plugins. This dependency must be removed.
It has to be investigated if the extension point org.eclipse.xtext.ui.shared.overridingGuiceModule can be used to achieve this.
- stakeholder: Spray developer
- keywords: Type: Task, Priority: Low, Plug-in structure
- status: READY

## issue0036 (FunctionalRequirement)
Provide documentation plugin
- stakeholder: Spray developer
- keywords: Type: Task, Component: Documentation
- status: DONE

## issue0037 (FunctionalRequirement)
Remove extension keyword
- stakeholder: Diagram editor creator
- keywords: Priority: Medium, Type: Enhancement, Component: Language
- status: DONE

## issue0038 (FunctionalRequirement)
The referenced package 'http://www.eclipse.org/xtext/common/JavaVMTypes' was imported from a different location.
- stakeholder: Spray developer
- keywords: Priority: Medium, Type: Defect, Component: Build
- status: DONE

## issue0039 (FunctionalRequirement)
Use spray.target in the build
- stakeholder: Spray developer
- keywords: Type: Task, Component: Build
- status: DONE

## issue0040 (FunctionalRequirement)
Error in code generation of CreateConnectionFeatures array in feature provider
- stakeholder: Diagram editor creator
- keywords: Priority: Medium, Type: Defect, Component: Code generator
- status: DONE

## issue0041 (FunctionalRequirement)
Upgrade to Tycho 0.13.0
- stakeholder: Spray developer
- keywords: Type: Task, Component: Build
- status: DONE

## issue0042 (FunctionalRequirement)
Compartments
- stakeholder: Diagram editor creator
- keywords: Priority: Medium, Type: Enhancement, Component: Language, Component: Code generator, Shapes DSL
- status: DONE

## issue0043 (FunctionalRequirement)
Compilation errors in wizard-generated project
- stakeholder: Diagram editor creator
- keywords: Priority: Medium, Type: Defect, Component: Code generator, Spray project wizard
- status: DONE

## issue0044 (FunctionalRequirement)
Compilation errors in wizard-generated project: Couldn't resolve reference to JvmIdentifiableElement
- stakeholder: Diagram editor creator
- keywords: Priority: Medium, Type: Defect, Component: Code generator, Spray project wizard
- status: DONE

## issue0045 (FunctionalRequirement)
Allow usage of genmodel in workspace
- stakeholder: Diagram editor creator
- keywords: Priority: Medium, Type: Defect, Component: Language
- status: DONE

## issue0046 (FunctionalRequirement)
Couldn't resolve reference to Module 'org.eclipselabs.spray.xtext.generator.SprayGenerator'.
- stakeholder: Diagram editor creator
- keywords: Priority: Low, Type: Defect, Component: Code generator
- status: DONE

## issue0047 (FunctionalRequirement)
mod4j-busmod.properties projectPath not consistent usable in build and in Eclipse
- stakeholder: Spray developer
- keywords: Priority: Medium, Type: Defect, Component: Build, Properties file
- status: DONE

## issue0048 (FunctionalRequirement)
Sign Jars
The resulting Jars are unsigned. We have to sign them in the build.
Question: Were to get a key from?
We would need a valid certificate. We won't get the funding yet.
--> Postponed
- stakeholder: Spray developer
- keywords: Priority: Medium, Type: Defect, Component: Build
- status: OPEN

## issue0049 (FunctionalRequirement)
Upgrade to Xtext 2.1.0
- stakeholder: Spray developer
- keywords: Priority: Medium, Type: Defect, Component: Build
- status: DONE

## issue0050 (FunctionalRequirement)
Palette contains group XXX
- stakeholder: Diagram editor user
- keywords: Priority: Medium, Type: Defect, Component: Code generator, Palette
- status: DONE

## issue0051 (FunctionalRequirement)
Code is not generated for example project
- stakeholder: Spray developer
- keywords: Priority: Medium, Type: Defect, Component: Build
- status: DONE

## issue0052 (FunctionalRequirement)
Provide possibility to set the file extensions of the businessmodel
- stakeholder: Diagram editor user
- keywords: Priority: Medium, Type: Enhancement, Component: Code generator
- status: DONE

## issue0053 (FunctionalRequirement)
Import org.eclipse.xtext.ecore is missing in graphiti generator
- stakeholder: Spray developer
- keywords: Priority: Critical, Type: Defect, Component: Build
- status: DONE

## issue0054 (FunctionalRequirement)
Automatic code generation does not work in runtime eclipse
- stakeholder: Diagram editor creator
- keywords: Priority: Critical, Type: Defect, Component: Code generator
- status: DONE

## issue0055 (FunctionalRequirement)
maven clean deletes org.eclipselabs.spray.xtext.jvmmodel.SprayJvmModelInferrer (java class)
- stakeholder: Spray developer
- keywords: Priority: Medium, Type: Defect, Component: Build
- status: DONE

## issue0056 (FunctionalRequirement)
Plugin providers injection as singleton
- stakeholder: Spray developer
- keywords: Priority: Medium, Type: Defect, Component: Code generator
- status: DONE

## issue0057 (FunctionalRequirement)
eContainer should be selectable for connection ends
The from and to attribute of a connection should accept eContainer.
This allows modelling connections for which one of the ends is the semantic container. E.g UML Generalization.
class Generalizaton :
connection (width=1) [
from eContainer;
to general;
]
Currently eContainer is not available, since it is an eOperation property of EObject Class and not an eStructuralFeature.
- stakeholder: Diagram editor creator
- keywords: Type: Enhancement, Priority: Medium, Component: Language, Spray DSL, Component: Code generator, Connection
- status: OPEN

## issue0058 (FunctionalRequirement)
A business element should be attachable to diagrams
- stakeholder: Diagram editor creator
- keywords: Priority: Medium, Type: Enhancement, Component: Language, Component: Code generator
- status: DONE

## issue0059 (FunctionalRequirement)
Vertical resize of containers is ignored
- stakeholder: Diagram editor creator
- keywords: Priority: Low, Type: Defect, Component: Code generator
- status: DONE

## issue0060 (FunctionalRequirement)
Connections should have a container Property
- stakeholder: Diagram editor creator
- keywords: Priority: Medium, Type: Defect, Component: Language, Component: Code generator
- status: DONE

## issue0061 (FunctionalRequirement)
Custom Figures
- stakeholder: Diagram editor creator
- keywords: Priority: Medium, Type: Enhancement, Component: Language, Shapes DSL
- status: DONE

## issue0062 (FunctionalRequirement)
Spray Editor must close when project closes
- stakeholder: Diagram editor creator
- keywords: Priority: Medium, Type: Defect, Component: UI
- status: DONE

## issue0063 (FunctionalRequirement)
Files generated into folder with project name
- stakeholder: Diagram editor creator
- keywords: Priority: Medium, Type: Defect, Component: Code generator
- status: DONE

## issue0064 (FunctionalRequirement)
SprayUserGuide.pdf Install introduction update sites url wrong
- stakeholder: Diagram editor creator
- keywords: Priority: Medium, Type: Defect, Component: Documentation
- status: DONE

## issue0065 (FunctionalRequirement)
SprayUserGuide.pdf: Choose the Diagram Type busmod
- stakeholder: Diagram editor creator
- keywords: Priority: Medium, Type: Defect, Component: Documentation
- status: DONE

## issue0066 (QualityRequirement)
Language should use curly brackets
- stakeholder: Diagram editor creator
- keywords: Priority: Medium, Type: Defect, Component: Language, Usability
- status: DONE

## issue0067 (FunctionalRequirement)
Develop Shapes DSL
- stakeholder: Diagram editor creator
- keywords: Type: Task, Component: Language, Shapes DSL, Component: Code generator
- status: DONE

## issue0068 (QualityRequirement)
Improve default look and feel
- stakeholder: Diagram editor user
- keywords: Type: Task, Component: Code generator, Usability, Generated diagram editor
- status: DONE

## issue0069 (FunctionalRequirement)
Add aliases for Shape elements
- stakeholder: Diagram editor creator
- keywords: Priority: Medium, Type: Enhancement, Component: Language
- status: DONE

## issue0070 (FunctionalRequirement)
Xtext Grammar shows error Cannot find compatible feature type in sealed EClass
- stakeholder: Diagram editor creator
- keywords: Priority: Medium, Type: Defect, Component: Language
- status: DONE

## issue0071 (FunctionalRequirement)
Fix alias for metaclasses
- stakeholder: Diagram editor creator
- keywords: Type: Task, Component: Code generator
- status: DONE

## issue0072 (QualityRequirement)
Improve formatter for the Spray DSL
- stakeholder: Diagram editor creator
- keywords: Priority: Low, Type: Enhancement, Component: Language, Spray DSL
- status: DONE

## issue0073 (FunctionalRequirement)
Class is regenerated in src-gen although it has been moved to src before
- stakeholder: Diagram editor creator
- keywords: Priority: Medium, Type: Defect, Component: Code generator
- status: DONE

## issue0074 (FunctionalRequirement)
Properties View does not work anymore
- stakeholder: Diagram editor user
- keywords: Priority: High, Type: Defect, Generated diagram editor, Component: Code generator, Properties view
- status: DONE

## issue0075 (FunctionalRequirement)
alias specification not applied to property classes generation
No fix needed: There is opnly one property sheet for a domain class, therefore all aliases can use the property sheet of their domain class. There is no need for a separate property sheet for an alias
- stakeholder: Diagram editor creator
- keywords: Priority: Medium, Type: Defect, Component: Code generator
- status: DONE

## issue0076 (FunctionalRequirement)
Layout application not appropriate
Won't fix: This old way of doing containers is now replaced by the compartments integrated into the shape DSL. This issue is therefore not relevant anymore.
- stakeholder: Diagram editor creator
- keywords: Priority: Low, Type: Enhancement, Component: Language, Shapes DSL, Component: Code generator, Generated diagram editor, Compartments
- status: DONE

## issue0077 (QualityRequirement)
Palette definition not intuitive
When I first defined a diagram editor in the Spray DSL, I wrote something like that:
class State :
container ( )
{
text ( ) { name };
}
Then I opened the diagram editor and wondered, that there is no palette. I found out, that I have to define additionally
behavior {
create palette "PaletteName";
}
I think this counterintuitive. First, an entry in the palette is essential. By default Graphiti defines the compartments Objects and Connections and put nodes in Objects and References in Connections. The Spray Generator always overrides the IPaletteCompartmentEntry[] getPalette() method in the ToolBehaviourProviderBase, so if you forget to define the palette, you get surprised.
That the palette is managed as a behavior is a technical aspect of Graphiti and is not obvious to the user.
I would suggest defining palette this way:
paletteCompartments {
classes alias "The classes"
references alias "The references"
}
class State :
paletteCompartment classes
container ( )
{
text ( ) { name };
}
If there is no palette compartments defined the getPalette() in ToolBehaviourProviderBase should not be overridden or at least the code in the overridden method should call super.getPalette().
This is just a proposal, have your thoughts on it.
Just a side note, the referenced attributes types there seems no way to define the palette compartment, they are always placed in a compartment named Create. With my proposal, you can write that:
paletteCompartments {
...
attributes alias "The attributes"
}
class ...:
container ... {
...
reference actions attribute name palette attributes
}
- stakeholder: Diagram editor creator
- keywords: Type: Enhancement, Priority: Low, Component: Language, Spray DSL, Usability, Palette
- status: OPEN

## issue0078 (FunctionalRequirement)
References should only be allowed to containment features
- stakeholder: Diagram editor creator
- keywords: Priority: Medium, Type: Defect, Component: Language, Spray DSL
- status: DONE

## issue0079 (FunctionalRequirement)
Provide ability of semantic validation in the diagrams
In Graphiti you can use decorators, e.g. add a warn or error marker to an element in the diagram when it violates certain semantic rules.
Spray should support such validations. The validation rules could be defined either
* in generated Java gap classes or
* in the Spray DSL itself or
* if the domain model is Xtext based, their Java Validator might be reused
For defining decorators, the DefaultToolBehaviorProvider.getDecorators(PictogramElement pe) can be used.
With issue#93 XtextValidationDecoratorProvider is introduced. It implements the newly added interface IRenderingDecoratorProvider, which can be used from Spray specific tool behavior providers.
- stakeholder: Diagram editor creator
- keywords: Type: Enhancement, Priority: Low, Component: Language, Spray DSL, Validation
- status: OPEN

## issue0080 (FunctionalRequirement)
Metamodel Cleanup
- stakeholder: Spray developer
- keywords: Priority: Medium, Type: Task, Component: Language
- status: DONE

## issue0081 (FunctionalRequirement)
Upgrade to Xtext 2.1.1
- stakeholder: Spray developer
- keywords: Type: Task, Component: Build
- status: DONE

## issue0082 (FunctionalRequirement)
Rename Behaviour to Behavior
- stakeholder: Diagram editor creator
- keywords: Priority: Medium, Type: Defect, Component: Language, Usability
- status: DONE

## issue0083 (FunctionalRequirement)
Spray UI Activator does not start when genmodel cannot be registered
- stakeholder: Diagram editor creator
- keywords: Priority: Medium, Type: Defect, Component: Language
- status: DONE

## issue0084 (FunctionalRequirement)
default package name in Spray project wizard
- stakeholder: Diagram editor creator
- keywords: Priority: Low, Type: Defect, Spray project wizard
- status: DONE

## issue0085 (FunctionalRequirement)
Model EClass wizard
- stakeholder: Diagram editor creator
- keywords: Priority: Medium, Type: Defect, Spray project wizard
- status: DONE

## issue0086 (FunctionalRequirement)
Please explain, how to support Graphiti default shapes
Currently there is already a rule Rectangle in the Spray DSL, but the generator does not handle it yet. I naively tried to implement a further dispatch createShape operation for type Rectangle, but ended up with a lot of compilation errors in other parts of the generated code.
There is lot of registrations and setting properties, I did not understand. For creating good looking diagrams (color gradients and so on), at least the default shapes should be supported. But for that, there must exist an understanding, how the code works and how the code can be (in first sight manually) extended to introduce rectangles.
def dispatch createShape (Rectangle rectangle) '''
«val varname = rectangle.shapeName.toFirstLower»
// Part is Rectangle
{
String type = "«rectangle.fullyQualifiedName»";
// create shape for text and set text graphics algorithm
Shape «varname» = peCreateService.createShape(textContainer, false);
Rectangle rectangle = gaService.createRectangle(getDiagram());
rectangle.setBackground(manageColor(«rectangle.lineColor»));
rectangle.setForeground(manageColor(«rectangle.fillColor»));
gaService.setLocationAndSize(rectangle, 0, 0, 0, 0);
peService.setPropertyValue(«varname», "MODEL_TYPE", type);
peService.setPropertyValue(«varname», ISprayContainer.CONCEPT_SHAPE_KEY, ISprayContainer.RECTANGLE);
// create link and wire it
link(«varname», addedModelElement);
}
'''
- stakeholder: Spray Developer
- keywords: Type: Task, Priority: Low, Spray DSL, Shapes DSL, Component: Code generator
- status: OPEN

## issue0087 (FunctionalRequirement)
Build fails while testing
- stakeholder: Spray Developer
- keywords: Operating System: Windows, Priority: Medium, Type: Defect, Component: Build
- status: DONE

## issue0088 (FunctionalRequirement)
New Spray Project Wizard and files without an extension
- stakeholder: Diagram editor creator
- keywords: Priority: Medium, Type: Defect, Spray project wizard
- status: DONE

## issue0089 (FunctionalRequirement)
Copy generated plugin.xml to project root until deactivated
When starting with a new project, the plugin.xml is generated to the src-gen folder. It must be manually copied and merged to the project root.
Usually during start up of a project it is not required to make manual changes, so the plugin.xml should be overwritten by default, until this feature is deactivated.
This should be either be configured through the Spray properties file, or by leveraging Output configurations. This may also be combined, so that the runtime OutputConfigurationProvider evaluates the Spray properties file.
there should be a property in properties file (and an option in the project creation wizard before):
override.plugin.xml
with possible values:
* yes: always overridden by each generation
* no: never overridden by each generation
* ask: show a confirmation dialog to the user to let him decide whether to override the file - this dialog should be only shown if the new plug-in.xml would differ from the existing one.
alternative solution: http://5ise.quanxinquanyi.de/2013/01/11/avoiding-manual-merge-when-generating-plugin-xml-with-xtextxtend/?utm_source=rss&utm_medium=rss&utm_campaign=avoiding-manual-merge-when-generating-plugin-xml-with-xtextxtend
- stakeholder: Diagram editor creator
- keywords: Type: Defect, Priority: Medium, Component: Code generator, Usability, Properties file, Spray project wizard
- status: OPEN

## issue0090 (FunctionalRequirement)
Add Spray to Eclipse Marketplace
In order to get more installations of Spray the project should be integrated into the Eclipse Marketplace.
According to the news there are already over 1 Million software installations done through the Marketplace.
[http://www.heise.de/open/meldung/Ueber-1-Million-Installationen-ueber-den-Eclipse-Marketplace-1377957.html]
- stakeholder: Spray developer
- keywords: Type: Task, Priority: Medium, Project marketing
- status: OPEN

## issue0091 (FunctionalRequirement)
Evaluate ZEST Layout Feature
- stakeholder: Diagram editor creator
- keywords: Priority: Medium, Type: Enhancement, Generated diagram editor
- status: DONE

## issue0092 (FunctionalRequirement)
Split CI builds
- stakeholder: Spray developer
- keywords: Priority: Medium, Type: Task, Component: Build
- status: DONE

## issue0093 (FunctionalRequirement)
Introduce runtime plugin for Xtext related extensions
- stakeholder: Spray developer
- keywords: Type: Enhancement, Plug-in structure
- status: DONE

## issue0094 (FunctionalRequirement)
Use xtend-maven-plugin, remove xtend-gen sources from repository
- stakeholder: Spray developer
- keywords: Priority: Medium, Type: Enhancement, Component: Build
- status: DONE

## issue0095 (FunctionalRequirement)
Upgrade to Xtext 2.2.0
- stakeholder: Spray developer
- keywords: Type: Task, Component: Build
- status: DONE

## issue0096 (FunctionalRequirement)
name in source.name cannot be resolved anymore
- stakeholder: Diagram editor creator
- keywords: Priority: Medium, Type: Defect, Component: Code generator
- status: DONE

## issue0097 (FunctionalRequirement)
Creating a new project with Spray Wizard fails because RegisterPlatformGenmodelListener is null
- stakeholder: Diagram editor creator
- keywords: Priority: Medium, Type: Defect, Spray project wizard
- status: DONE

## issue0098 (FunctionalRequirement)
Content propsoal in Styles DSL Editor causes exception
- stakeholder: Diagram editor creator
- keywords: Priority: Medium, Styles DSL, Type: Defect, Component: Language, Component: UI
- status: DONE

## issue0099 (FunctionalRequirement)
Shape Generator runs on NPE
- stakeholder: Diagram editor creator
- keywords: Priority: Medium, Shapes DSL, Type: Defect, Component: Code generator
- status: DONE

## issue0100 (FunctionalRequirement)
Styles postprocessor classes must be compiled in separate module
- stakeholder: Diagram editor creator
- keywords: Priority: High, Type: Defect, Component: Code generator, Styles DSL
- status: DONE

## issue0101 (FunctionalRequirement)
Compartment entry has no displayed name
- stakeholder: Diagram editor user
- keywords: Priority: Medium, Type: Defect, Generated diagram editor, Component: Code generator
- status: DONE

## issue0102 (FunctionalRequirement)
Displayed shape name is incomplete
- stakeholder: Diagram editor user
- keywords: Priority: Medium, Type: Defect, Generated diagram editor, Component: Code generator
- status: DONE

## issue0103 (FunctionalRequirement)
Shapes are not movable anymore
- stakeholder: Diagram editor user
- keywords: Priority: Medium, Type: Defect, Generated diagram editor, Component: Code generator
- status: DONE

## issue0104 (FunctionalRequirement)
Metamodel import from developer workspace in DSL not resolvable
- stakeholder: Diagram editor user
- keywords: Priority: Low, Type: Defect, Component: UI, Component: Language, Spray DSL
- status: DONE

## issue0105 (FunctionalRequirement)
Allow more than one connection reference with node definition
- stakeholder: Diagram editor user
- keywords: Priority: High, Type: Defect, Component: Language, Spray DSL
- status: DONE

## issue0106 (FunctionalRequirement)
Code generator assumes fix name attribute at EClass instances
- stakeholder: Diagram editor user
- keywords: Priority: High, Type: Defect, Component: Code generator
- status: DONE

## issue0107 (FunctionalRequirement)
CreateConnectionFeature List in FeatureProvider lacks comma
- stakeholder: Diagram editor user
- keywords: Priority: High, Type: Defect, Component: Code generator
- status: DONE

## issue0108 (FunctionalRequirement)
references to containments in the references { } section of a class are not supported yet
Won't fix: As this kind of container will be replaced by the new compartments in the shape DSL, this issue is no longer relevant.
- stakeholder: Diagram editor user
- keywords: Priority: Low, Type: Enhancement, Component: Language, Spray DSL, Compartments
- status: DONE

## issue0109 (FunctionalRequirement)
Add implicit import for java.lang
- stakeholder: Diagram editor user
- keywords: Priority: Medium, Type: Enhancement, Component: Language, Shapes DSL
- status: DONE

## issue0110 (FunctionalRequirement)
Remove description attribute, use multi-line type functional comment instead
- stakeholder: Diagram editor user
- keywords: Priority: Medium, Type: Enhancement, Component: Language, Styles DSL
- status: DONE

## issue0111 (FunctionalRequirement)
Shape Formatter
- stakeholder: Diagram editor user
- keywords: Priority: Medium, Type: Defect, Component: Language, Shapes DSL, Component: UI, Usability
- status: DONE

## issue0112 (FunctionalRequirement)
Shape Outline
- stakeholder: Diagram editor user
- keywords: Priority: Medium, Type: Defect, Component: UI, Shapes DSL
- status: DONE

## issue0113 (FunctionalRequirement)
SPRAY imports are not verified
- stakeholder: Diagram editor user
- keywords: Priority: Medium, Type: Defect, Component: Language, Spray DSL, Validation
- status: DONE

## issue0114 (FunctionalRequirement)
Shape parameters shall be used in any assignment
shape FormShape(java.lang.String formqualified) {
rectangle {
position(x=0,y=0)
size(width=60,height=20)
text {
align(horizontal=center, vertical=middle)
position(x=5, y=5)
size(width=60,height=20)
value=formqualified
}
}
}
Currently it is not possible to use a supplied parameter for position, width etc.
Really nice would be:
shape FormShape(java.lang.String formqualified, java.lang.Integer shapewidth) {
rectangle {
position(x=0,y=0)
size(width=shapewidth,height=20)
text {
align(horizontal=center, vertical=middle)
position(x=5, y=5)
size(width=shapewidth,height=20)
value=formqualified
}
}
}
I'm aware of, that isn't that easy and raises further issues. On the other hand it opens many possibilities.
- stakeholder: Diagram editor creator
- keywords: Type: Enhancement, Priority: Low, Component: Language, Shapes DSL, Size & position
- status: OPEN

## issue0115 (FunctionalRequirement)
Support arithmetic operations within shapes
shape FormShape(java.lang.String formqualified) {
rectangle {
position(x=0,y=0)
size(width=60,height=20)
text {
align(horizontal=center, vertical=middle)
position(x=5, y=5)
size(width=60,height=20)
value=formqualified
}
}
}
Currently width etc are all integer constants. Nice would be to use arithmetic expressions. This would be very handy on complexer Shapes.
- stakeholder: Diagram editor creator
- keywords: Type: Enhancement, Priority: Low, Component: Language, Shapes DSL, Size & position
- status: OPEN

## issue0116 (FunctionalRequirement)
Access to Graphiti Diagram Units
It would be very handy to have access to Graphiti Diagram Units.
- stakeholder: Diagram editor creator
- keywords: Type: Enhancement, Priority: Medium, Component: Language, Shapes DSL, Size & position
- status: OPEN

## issue0117 (FunctionalRequirement)
Nested Shaped References
It would be very handy to have nested Shape References (Reuse of already defined shapes, or even externally defined shapes -- or even reference Shape Libraries)
shape A {
}
shape B {
}
shape C {
shape A {
assignments
}
shape B {
assignments
}
}
- stakeholder: Diagram editor creator
- keywords: Type: Enhancement, Priority: Medium, Component: Language, Shapes DSL, Compartments
- status: IN_PROGRESS

## issue0118 (FunctionalRequirement)
Allow import in shapes
- stakeholder: Diagram editor creator
- keywords: Priority: Medium, Type: Defect, Component: Language, Shapes DSL
- status: DONE

## issue0119 (FunctionalRequirement)
icon path shall be relative to project root
Won't fix: warning sufficient for missing icon
- stakeholder: Diagram editor creator
- keywords: Priority: Medium, Type: Defect, Component: Language, Spray DSL
- status: DONE

## issue0120 (FunctionalRequirement)
Font-Selector shall also define selected size
Font-Selector is nice, but it should also define font-size etc. if data is available, which may not be the case on all plattforms, but shall not override existing values.
- stakeholder: Diagram editor creator
- keywords: Type: Enhancement, Priority: Medium, Component: Language, Styles DSL, Usability
- status: OPEN

## issue0121 (FunctionalRequirement)
Shape: Image support is missing
There is not image support within shapes.
shape <ShapeIdent> {
image {
...
}
}
or
shape <ShapeIdent> {
image(...)
}
The following code that is currently manually to write should be generated:
http://groups.google.com/group/spray-users/msg/1b3856103b6c7353
- stakeholder: Diagram editor creator
- keywords: Type: Enhancement, Priority: Medium, Component: Language, Shapes DSL
- status: OPEN

## issue0122 (FunctionalRequirement)
Shape settings have no effect
- stakeholder: Diagram editor creator
- keywords: Priority: Medium, Type: Enhancement, Component: Language, Shapes DSL
- status: DONE

## issue0123 (FunctionalRequirement)
Make generator extensible without need to change the source
- stakeholder: Diagram editor creator
- keywords: Priority: Medium, Type: Defect, Component: Code generator
- status: DONE

## issue0124 (FunctionalRequirement)
Spray Generators do not respect genmodel settings
- stakeholder: Diagram editor creator
- keywords: Priority: Medium, Type: Defect, Component: Code generator
- status: DONE

## issue0125 (FunctionalRequirement)
Installation instructions
- stakeholder: Diagram editor creator
- keywords: Priority: Medium, Type: Defect, Component: Documentation, Component: Build
- status: DONE

## issue0126 (FunctionalRequirement)
askFor has no effect for connections
- stakeholder: Diagram editor user
- keywords: Priority: Medium, Type: Defect, Component: Code generator
- status: DONE

## issue0127 (FunctionalRequirement)
Couldn't resolve reference to root EClass of a model
- stakeholder: Diagram editor creator
- keywords: Priority: Critical, Type: Defect, Component: Language, Spray DSL, Component: UI
- status: DONE

## issue0128 (FunctionalRequirement)
Spray update site doesn't work anymore
- stakeholder: Diagram editor creator
- keywords: Priority: Medium, Type: Defect, Component: Build
- status: DONE

## issue0129 (FunctionalRequirement)
Installation into Eclipse Juno
- stakeholder: Diagram editor creator
- keywords: Priority: Medium, Type: Defect, Component: Build
- status: DONE

## issue0130 (FunctionalRequirement)
Add SVG Shape Generator
- stakeholder: Diagram editor creator
- keywords: Priority: Medium, Type: Enhancement, Component: Code generator, Shapes DSL, SVG
- status: DONE

## issue0131 (FunctionalRequirement)
Reduce plugin dependencies of Spray diagram plugin
- stakeholder: Spray developer
- keywords: Priority: Medium, Type: Defect, Component: Build
- status: DONE

## issue0132 (FunctionalRequirement)
Develop Spray Diagram for Shapes DSL
I got already multiple times feedback that a visual editor for Shapes would be desired. And why not develop such an editor with Spray itself? It should be doable with Spray and a good proof by eating our own dogfood.
- stakeholder: Diagram editor creator
- keywords: Type: Enhancement, Priority: Low, Component: Language, Shapes DSL, Usability
- status: OPEN

## issue0133 (FunctionalRequirement)
Switch from AbstractModelInferrer to IJvmDeclaredTypeAcceptor
- stakeholder: Spray developer
- keywords: Priority: Medium, Type: Enhancement, Component: Code generator
- status: DONE

## issue0134 (FunctionalRequirement)
Installation of Spray via Release Update Site fails because of missing dependencies
- stakeholder: Diagram editor creator
- keywords: Priority: Medium, Type: Defect, Component: Build
- status: DONE

## issue0135 (FunctionalRequirement)
Spray cannot resolve reference to JvmIdentifiableElements like eClass and name when using custom ecore
- stakeholder: Diagram editor creator
- keywords: Priority: Medium, Type: Defect, Component: Build
- status: DONE

## issue0136 (FunctionalRequirement)
Xtext tests that do not suppress serialization fail on Windows
- stakeholder: Spray developer
- keywords: Priority: Medium, Type: Defect, Component: Test, Component: Build
- status: DONE

## issue0137 (FunctionalRequirement)
Unable to load ExecutableExtensionFactory
- stakeholder: Diagram editor user
- keywords: Priority: High, Type: Defect, Component: Build, Generated diagram editor
- status: DONE

## issue0138 (FunctionalRequirement)
Initially generated *DefaultStyle.java does not compile
- stakeholder: Diagram editor creator
- keywords: Priority: Medium, Type: Defect, Component: Code generator
- status: DONE

## issue0139 (FunctionalRequirement)
Install cannot be completed due to conflicting dependencies
- stakeholder: Diagram editor creator
- keywords: Priority: High, Type: Defect, Component: Build
- status: DONE

## issue0140 (FunctionalRequirement)
Shape preview in Xtext hover
- stakeholder: Diagram editor creator
- keywords: Priority: Low, Type: Enhancement, Component: Language, Spray DSL, Shapes DSL, Component: UI, Usability
- status: DONE

## issue0141 (FunctionalRequirement)
Context menu entry Show properties view predefined
A very common use case is to show the properties for a selected element in generated diagram editor.
When the properties is not opened yet you currently have to use Window -> Show View -> Others -> General/Properties.
There should be a context menu entry available for every graphical element that should trigger to open respectively (re-)activate the properties view.
This context menu entry could be proposed as predefined custom behavior inside the Spray DSL editor.
- stakeholder: Diagram editor user
- keywords: Type: Enhancement, Priority: Low, Generated diagram editor, Usability, Properties view
- status: OPEN

## issue0142 (FunctionalRequirement)
Enable linking to referenced domain model element
- stakeholder: Diagram editor creator
- keywords: Priority: Medium, Type: Defect, Component: Language, Spray DSL, Component: UI
- status: DONE

## issue0143 (FunctionalRequirement)
Migrated connection DSL template proposal to new syntax
- stakeholder: Diagram editor creator
- keywords: Priority: Medium, Type: Defect, Component: Language, Spray DSL, Component: UI
- status: DONE

## issue0144 (FunctionalRequirement)
Fix create behavior template askFor reference
- stakeholder: Diagram editor creator
- keywords: Priority: Medium, Type: Defect, Component: Language, Spray DSL, Component: UI
- status: DONE

## issue0145 (FunctionalRequirement)
Adapt Spray DSL formatter to syntax changes
- stakeholder: Diagram editor creator
- keywords: Priority: Low, Type: Defect, Component: Language, Spray DSL, Component: UI
- status: DONE

## issue0146 (FunctionalRequirement)
Include all example projects into the automated build
Currently only org.eclipselabs.spray.examples.one is included.
The following projects have to be included:
* BPMN
* de.htwg.2012.bpmn.mm
* org.eclipselabs.spray.examples.bpmn
* LWC 2012
* de.htwg.2012.lwc.mm
* org.eclipselabs.spray.examples.lwc2012
* Petrinets
* de.htwg.petrinet.mm
* org.eclipselabs.spray.examples.petrinet
* Fowler DSL / Statemachine
What actions are required for the inclusion?
* mavenize projects
* add mwe2 Workflows for starting the generators (style, shape, spray)
* clean up and extend projects if necessary (Fowler DSL, styles and shapes in example.one)
A successful build of the example projects is always a helpful indicator of a working Spray.
* add to modules in releng pom
- stakeholder: Spray developer
- keywords: Type: Task, Priority: High, Examples, Component: Build
- status: OPEN

## issue0147 (QualityRequirement)
Document JaCoCo setup in Spray developer documentation
The Spray build supports code coverage measurement via JaCoCo. This should be documented in the Spray developer guide.
- stakeholder: Spray developer
- keywords: Type: Task, Priority: Low, Component: Build, Component: Documentation
- status: OPEN

## issue0148 (QualityRequirement)
Document Sonar in Spray developer guide
The Spray build supports metrics collection via Sonar. This should be documented in the Spray developer guide. The guide should also cover which components are to exclude from investigation (how to exclude the generated code parts). Further the usage of Sonar (web interface as well as Eclipse plug-in) should be shown.
- stakeholder: Spray developer
- keywords: Type: Task, Priority: Low, Component: Build, Component: Documentation
- status: OPEN

## issue0149 (FunctionalRequirement)
Investigate out of memory in xtend-maven-plugin in local build
- stakeholder: Spray developer
- keywords: Priority: Low, Type: Task, Component: Build
- status: DONE

## issue0150 (QualityRequirement)
Improve performance of domain model completion in Spray DSL
- stakeholder: Diagram editor creator
- keywords: Priority: Medium, Type: Enhancement, Component: Language, Spray DSL, Component: UI, Performance
- status: DONE

## issue0151 (FunctionalRequirement)
comments in Shape and Styles DSL are not colored like comments
- stakeholder: Diagram editor creator
- keywords: Priority: Low, Type: Defect, Component: Language, Shapes DSL, Styles DSL, Component: UI
- status: DONE

## issue0152 (FunctionalRequirement)
A generated Spray projects in Juno still imports org.eclipse.xtext.xtend2.lib
- stakeholder: Diagram editor creator
- keywords: Priority: Medium, Type: Defect, Component: Code generator
- status: DONE

## issue0153 (FunctionalRequirement)
org.eclipselabs.spray.styles not included in generated MANIFEST.MF
- stakeholder: Diagram editor creator
- keywords: Priority: Medium, Type: Defect, Component: Code generator
- status: DONE

## issue0154 (FunctionalRequirement)
Empty compartment name for connection
- stakeholder: Diagram editor user
- keywords: Priority: Medium, Type: Defect, Component: Code generator, Generated diagram editor
- status: DONE

## issue0155 (QualityRequirement)
Prepare Spray 0.5 release
We should make a release of the current state of Spray as Spray 0.5.
* refresh documentation (user, developer)
* fix tests
* Juno version
* Indigo version? (should a Indigo version maintained, what about branches, should the eclipse_juno branch switched to master, and the current master as eclipse_indigo?)
* what about a Spray product build
* other things.
- stakeholder: Spray developer
- keywords: Type: Task, Priority: High, Component: Build, Examples, Component: Documentation, Component: Test, Quality assurance, Release
- status: OPEN

## issue0156 (FunctionalRequirement)
NPE at SprayScopeProvider.scope_Connection_from
- stakeholder: Diagram editor creator
- keywords: Priority: Medium, Type: Defect, Component: Language, Spray DSL, Component: UI
- status: DONE

## issue0157 (FunctionalRequirement)
A bulk of PackageNotFoundExceptions after each Scope call
- stakeholder: Diagram editor creator
- keywords: Priority: Medium, Type: Defect, Component: Language, Spray DSL, Component: UI
- status: DONE

## issue0158 (FunctionalRequirement)
Exception at save of diagram file edited with generated Graphiti editor
- stakeholder: Diagram editor user
- keywords: Priority: Medium, Type: Defect, Component: Code generator, Generated diagram editor
- status: DONE

## issue0159 (FunctionalRequirement)
ClassCastException when creating new diagram shape
- stakeholder: Diagram editor creator
- keywords: Priority: Medium, Type: Defect, Component: UI, Component: Language, Shapes DSL
- status: DONE

## issue0160 (FunctionalRequirement)
Referencing a style definition has no effect
- stakeholder: Diagram editor user
- keywords: Priority: High, Type: Defect, Component: Code generator, Generated diagram editor
- status: DONE

## issue0161 (FunctionalRequirement)
Link referenced shapes and styles definition not only to the generated Java file
- stakeholder: Diagram editor creator
- keywords: Priority: Medium, Type: Enhancement, Component: Language, Shapes DSL, Styles DSL, Component: UI
- status: DONE

## issue0162 (FunctionalRequirement)
Propose gradient definition also at style attribute within shape definition
- stakeholder: Diagram editor creator
- keywords: Priority: Low, Type: Defect, Component: Language, Shapes DSL
- status: DONE

## issue0163 (QualityRequirement)
Better auto completion support in Shape and Styles DSL
- stakeholder: Diagram editor creator
- keywords: Priority: Medium, Type: Enhancement, Usability, Component: Language, Shapes DSL, Styles DSL
- status: DONE

## issue0164 (QualityRequirement)
Sort / prioritize elements in proposals
- stakeholder: Diagram editor creator
- keywords: Priority: Low, Type: Enhancement, Spray DSL, Component: Language, Component: UI, Usability
- status: DONE

## issue0165 (FunctionalRequirement)
Write a concept / overview of all scenarios creating diagram elements
Currently there are quite a lot of restrictions in building up an domain model by creation of diagram elements. It should be documented inside the developer guide or in a wiki page, which creation scenarios are thinkable and whose of them are already support resp. what have to be done in Spray to enable the not yet supported scenarios.
Some examples:
* handling of containment and non-containment relationships in the domain meta model
* handling of recursion in the domain meta model
* handling of the scenario, where multiple diagram elements maps to one domain model element / feature
* handling of the scenario, where one diagram element maps to multiple domain model elements / features
* handling of the scenario, where the existence / appearance of a diagram element depends on value of domain model features
* handling of the scenario, where the existence / appearance of a diagram element depends on the existence of a certain structure in the domain model
* handling of the scenario, where the a domain model element appears for better visibility multiple times in a diagram (example: level that appears in multiple hierarchies)
* handling of the scenario, where a containment relationship in the domain model is depicted as nested shapes in a diagram
* handling of the scenario, where a containment relationship in the domain model is depicted by (styled) connection lines between diagram elements
* other scenarios ...
- stakeholder: Spray developer
- keywords: Type: Task, Priority: Medium, Component: Documentation, Requirements engineering
- status: OPEN

## issue0166 (FunctionalRequirement)
Write scoping and proposal tests
use Xtext XPECT to define Scoping (and auto completion) tests
- stakeholder: Spray developer
- keywords: Type: Task, Component: Test, Component: Build
- status: IN_PROGRESS

## issue0167 (FunctionalRequirement)
Figures on the same level are marked as one would exeed the dimensions of the other
The following shape is marked with the warning: "The height of all subelements is bigger than max_height of the shape."
shape MyShape {
rectangle {
position(x=0,y=0)
size(width=50,height=50)
}
ellipse {
position(x=50,y=50)
size(width=50,height=150)
}
}
As the both figures have no common parent there should be no restriction in width and height (in Graphiti code these both figures may contained within a invisible rectangle that would receive the max dimension derived by width, height and position of its contained figures).
Only in the following the construct the validation would be ok, as the ellipse is nested inside the rectangle and thus should not exceed the dimensions of its containing figure:
shape MyShape2 {
rectangle {
position(x=0,y=0)
size(width=50,height=50)
ellipse {
position(x=5,y=5)
size(width=50,height=50)
}
}
}
If you have a look at the org.eclipselabs.spray.shapes.validation.ShapeJavaValidator that works with global variables, you see how tricky the calculation of the validation is.
- stakeholder: Diagram editor creator
- keywords: Priority: Medium, Type: Defect, Component: Language, Shapes DSL, Validation
- status: OPEN

## issue0168 (FunctionalRequirement)
Enable definition of connection by given start and end element
Currently there must exist a domain meta model element that can be mapped to a connection. This domain meta model element holds references to the start and the end element. But the more common case is, that there two elements that have uni- o bi-directional association to each other without such an extra third element.
In the DSL it should be possible, to write something like this:
classes Element1 alias e1, Element2 alias e2 {
connection ( )
{
from e1.element2Reference // this is the reference of type Element2
to e2.element1Reference // this is the reference of type Element1
}
}
In the example above there is a bi-directional association between Element1 and Element2 assumed. Note that there might be different association roles between Element1 and Element2 defined like Person.parents->Person*, Person.siblings->Person*
The following example shows the case when there is only a uni-directional relationship from Element2 to Element1, i.e. Element1 does not know that it is referenced by Element2:
classes Element1 alias e1, Element2 alias e2 {
connection ( )
{
from e1 // this is the reference of type Element2
to e2.element1Reference // this is the reference of type Element1
}
}
If there is only one relationship feature on each Element of the corresponding type the relationship feature may left off in the definition:
classes Element1 alias e1, Element2 alias e2 {
connection ( )
{
from e1 // this is the reference of type Element2
to e2 // this is the reference of type Element1
}
}
This is currently possible using:
class BusinessClass alias FullClass {
container ( fill=dark_green )
{
text ( ) { "<<"+eClass.name+">> " + name};
}
references {
superclass : connection( )
}
behavior {
create into types palette "Shapes" askFor name ;
}
The superclass is just an EReference in the domain model. I think it makes sense to define this inside the meta class in which the reference is defined, as is done here.
- stakeholder: Diagram editor creator
- keywords: Priority: Medium, Type: Enhancement, Component: Language, Spray DSL, Connection
- status: OPEN

## issue0169 (FunctionalRequirement)
Enable creation of element that are not direct children of the model root
Domain model:
A <>-ab- B
B <>-bc- D
Currently it is only possible to define
diagram aDiagram for A
class B {
...
behavior {
create into ab palette "Elements";
}
}
but it is not possible yet to define
class C {
...
behavior {
create into ab.bd palette "Elements";
}
}
(with ab.bd navigating from A to C over B, in the diagram the representation of C have to be nested into the representation of B).
Jos' answer: The ab.cd is only clear when you know from which B you start when creating a C. So you need to drag the C on top of B to create it, but then it would logically be rendered inside the B shape. This is how it works with compartments now. Howe else would you know to which B to add C.
Children of other nodes (except root) can be created inside compartments of their parent node.
- stakeholder: Diagram editor creator
- keywords: Priority: Medium, Type: Enhancement, Component: Language, Spray DSL, Compartments
- status: OPEN

## issue0170 (FunctionalRequirement)
Catch NPEs in model inferrer code
Won't fix: moved away from model inferer for now
- stakeholder: Spray developer
- keywords: Priority: Medium, Type: Defect, Component: Code generator, Component: Build
- status: DONE

## issue0171 (FunctionalRequirement)
Provide trace model for shape and style DSL
By switching style and shape DSL to use a model inferrer it would be nice to insert trace points in the model inferrer code to enable debugging between Shape DSL and generated Shape Java class resp. Style DSL and generated Style Java class.
- stakeholder: Diagram editor creator
- keywords: Priority: Low, Type: Enhancement
- status: OPEN

## issue0172 (FunctionalRequirement)
Add dynamic compartments to Shapes DSL
- stakeholder: Diagram editor user
- keywords: Priority: High, Type: Task, Component: Code generator, Component: Language, Shapes DSL, Generated diagram editor, Compartments
- status: DONE

## issue0173 (FunctionalRequirement)
Fix documentation before 0.5 release
- stakeholder: Diagram editor creator
- keywords: Priority: Medium, Type: Task, Component: Documentation
- status: OPEN

## issue0174 (FunctionalRequirement)
Add wizard option to decide about one file or two file model variant
Won't fix: In would like to reject this issue. Having the domain model stored in the same resource as the Graphiti model is nice for making a quick example, but these two things should in practice always be separated. I think it is bad design to combine them.
- stakeholder: Diagram editor user
- keywords: Priority: Low, Type: Enhancement, Component: Code generator, Spray project wizard, Generated diagram editor
- status: DONE

## issue0175 (FunctionalRequirement)
Have a look at setDoneChanges(true) in CreateFeature of Connections
- stakeholder: Diagram editor user
- keywords: Priority: Medium, Type: Defect, Component: Code generator
- status: DONE

## issue0176 (FunctionalRequirement)
Renable SVG generator after switch to model inferrer in Shapes DSL
- stakeholder: Diagram editor creator
- keywords: Priority: Medium, Type: Defect, Component: Code generator, SVG
- status: DONE

## issue0177 (FunctionalRequirement)
Enable linking to style and gradients under their simple name
- stakeholder: Diagram editor creator
- keywords: Priority: Medium, Type: Defect, Component: Language, Shapes DSL, Spray DSL, Component: UI, Usability
- status: DONE

## issue0178 (FunctionalRequirement)
Remove workaround for Duplicate JVMIdentifiableElement
Won't fix: moved away from model inferer for now
- stakeholder: Spray developer
- keywords: Priority: Low, Type: Defect, Component: Code generator
- status: DONE

## issue0179 (FunctionalRequirement)
Make Maven build work under Windows for projects using model inferrer
fixed: moved away from model inferer for now
- stakeholder: Spray developer
- keywords: Priority: Medium, Type: Defect, Component: Build
- status: DONE

## issue0180 (FunctionalRequirement)
IllegalArgumentException in DefaultSprayStyle
- stakeholder: Diagram editor user
- keywords: Priority: Medium, Type: Defect, Component: Code generator, Generated diagram editor
- status: DONE

## issue0181 (FunctionalRequirement)
Fix coordinates for SVG generation
- stakeholder: Diagram editor creator
- keywords: Type: Task, Component: Code generator, Shapes DSL, SVG
- status: DONE

## issue0182 (FunctionalRequirement)
Compartments can also be other shapes than rectangles
Currently a compartment is a rectangle (hard-coded). Instead the user should be able to define any closed shape (rectangle, rounded-rectangle, ellipse, polygon) as a compartment. Need to add this option to the DSL and to the code generator
- stakeholder: Diagram editor user
- keywords: Priority: Medium, Type: Task, Component: Code generator, Component: Language, Shapes DSL, Compartments
- status: READY

## issue0183 (FunctionalRequirement)
Nested compartments are selectable
- stakeholder: Diagram editor user
- keywords: Priority: Medium, Type: Defect, Component: Code generator, Component: Language, Shapes DSL, Compartments, Generated diagram editor
- status: DONE

## issue0184 (FunctionalRequirement)
SVG-generation folder
- stakeholder: Diagram editor creator
- keywords: Priority: Low, Type: Defect, Component: Code generator, Shapes DSL, SVG
- status: DONE

## issue0185 (FunctionalRequirement)
Gradient, Style and Shape Generator should support Generation Gap Pattern
The artifacts generated from the Spray DSL follow the Generation Gap Pattern, so that there is a base and a gap class generated for each artifact, where the Gap class may moved to src folder to adapt it with manually written code.
This should be true also for the artifacts derived from Gradient, Style and Shape definition.
- stakeholder: Diagram editor creator
- keywords: Type: Task, Component: Code generator, Shapes DSL, Styles DSL
- status: IN_PROGRESS

## issue0186 (FunctionalRequirement)
Gradient, Style and Shape generator should respect *.properties file entries
- stakeholder: Diagram editor creator
- keywords: Priority: Low, Type: Defect, Component: Code generator, Shapes DSL, Styles DSL, Properties file
- status: DONE

## issue0187 (FunctionalRequirement)
Integrate Xtext builder participants of DSLs with each other
Currently the builder participants / generators of the different DSLs do know nothing about each other. So a change e.g. in the Style DSL that has no effect to references to style definitions in other DSLs may break the Java code basis as the generated Style Java code may not be compatible to the other generated Java code that uses this code.
So it would be best practice to always trigger the generator for all DSL artifacts that are potentially affected by the change in a DSL artifact, e.g. the Shape generator is also invoked when a style has changed as a shape can reference a style.
scenarios:
1. *.style file changed
1.1 style file contains only style definitions
* (re-)generate the Java file for the style definition
* if a style name has changed (or even deleted) this makes all elements dirty that references this style (as the reference should be broken then):
* style definitions that have defined this style as super style
* shape and connection definitions that references this style
* mapping definitions in .spray files that references this style
* if the style references a gradient that has been not generated yet in Java this generation should be triggered within this build
* if the style references a super style that has been not generated yet in Java this generation should be triggered within this build
1.2 style file contains only gradient definitions
* (re-)generate the Java file for the gradient definition
* if a gradient name has changed (or even deleted) this makes all elements dirty that references this gradient (as the reference should be broken then):
* style definitions that references this gradient
1.3 style file contains gradient and style definitions
* apply first 1.2 and then 1.1 as styles may depend on existing Gradient Java files
2. *.shape file changed
* (re-)generate the Java file for the shape definition
* if a shape name has changed (or even deleted) this makes all elements dirty that references this shape (as the reference should be broken then):
* mapping definitions in .spray files that references this shape
* if the shape references a style that has been not generated yet in Java this generation should be triggered within this build
3. *.spray file changed
* (re-)generate the Java files derived from the mapping definitions (i.e. all Graphiti feature classes as well as some more Graphiti related classes)
* if in the Spray file a style is referenced that has been not generated yet in Java this generation should be triggered within this build
* if in the Spray file a shape is referenced that has been not generated yet in Java this generation should be triggered within this build
4. domain model changed
* this should make Spray files dirty that references elements from the domain model
5. Workspace start
* it should be checked if there already Java files generated for .spray, .shape and .style files contained in a project if not so, the generation should be triggered (so it is not necessary to make existing files dirty or call explicitly clear project to trigger the generation) - this check could be done e.g. in the Activator class
- stakeholder: Diagram editor creator
- keywords: Priority: Medium, Type: Enhancement, Component: Code generator, Component: UI
- status: READY

## issue0188 (FunctionalRequirement)
SVG-Generator Bugs (Size and Compartments)
* fixed position calculation (absolute and container relative works now)
* added style interpretation (currently only directly annotated style
information)
* added connection decoration interpretation
* still missing:
* font attribute interpretation
* interpretation of text align
* interpretation of placing's radius and angle,
* referenced style interpretation
* gradients interpretation
* color interpretation based on numbers
- keywords: Priority: Medium, Type: Defect, Component: Code generator, Shapes DSL, Styles DSL, SVG, Compartments
- status: IN_PROGRESS

## issue0189 (FunctionalRequirement)
Using Container and Shape together
Hi,
I'm trying to use the Container object with a Shape.
Something like this:
container()
{
shape myDecoratingShape {}
text ( ) { "<<"+capabilityName+">>" }
reference measurements attribute measurementName;
}
The problem is when I put a Shape (containing rectangles, etc...) inside a container and attempt to draw it,
all I get is a line.
I suppose what I really want to do is embed the container within the shape its self.
Is this possible and if so how do you go about doing it?
Jos' answer: Shapes and containers cannot be used together at this moment. I am working on integrating the containers into the shape DSL to allow exactly what you want. See issue http://code.google.com/a/eclipselabs.org/p/spray/issues/detail?id=172.
- stakeholder: Diagram editor user
- keywords: Priority: Medium, Type: Enhancement, Compartments, Component: Language, Spray DSL, Shapes DSL, Component: Code generator, Generated diagram editor
- status: READY

## issue0190 (FunctionalRequirement)
Define shape and style for anchors
Anchors currently are circles with light grey fill. It would ne nice to be able to use other shapes as anchors and to give them a style.
- stakeholder: Diagram editor user
- keywords: Priority: Low, Type: Enhancement, Component: Code generator, Component: Language, Shapes DSL
- status: READY

## issue0191 (FunctionalRequirement)
Spray model editor gets weird eception if properties file does not exist
- stakeholder: Diagram editor creator
- keywords: Priority: Critical, Type: Defect, Component: Code generator, Component: UI, Properties file
- status: DONE

## issue0192 (FunctionalRequirement)
Reference to EClass cannot be resolved in Juno Modelling + Graphiti + Spray
- stakeholder: Diagram editor creator
- keywords: Priority: Medium, Type: Defect, Component: Build
- status: DONE

## issue0193 (FunctionalRequirement)
Unhandled parameter types: [null] in SVG generator
- stakeholder: Diagram editor creator
- keywords: Priority: Medium, Type: Defect, SVG, Component: Code generator
- status: DONE

## issue0194 (FunctionalRequirement)
Moving of elements not working
- stakeholder: Diagram editor user
- keywords: Component: Code generator, Operating System: All, Priority: Critical, Type: Defect, Generated diagram editor
- status: DONE

## issue0195 (FunctionalRequirement)
AbortCompilation: Pb(324) - class cannot be resolved, indirectly referenced
I've had seen this from time to time, too. Maybe a problem with type inference, where the return type of method should be defined explicitly or there is a dependent library missing on the classpath, I will have a look at it.
https://bugs.eclipse.org/bugs/show_bug.cgi?id=352706
- stakeholder: Diagram editor user
- keywords: Priority: Medium, Type: Defect, Component: Code generator
- status: READY

## issue0196 (FunctionalRequirement)
NPE in adjustPriority(...)
- stakeholder: Diagram editor user
- keywords: Priority: Medium, Type: Defect, Component: Language, Spray DSL, Component: UI
- status: DONE

## issue0197 (FunctionalRequirement)
Change documentation to use compartments
- stakeholder: Diagram editor creator
- keywords: Priority: Medium, Type: Task, Component: Documentation, Compartments, Spray DSL, Shapes DSL
- status: DONE

## issue0198 (FunctionalRequirement)
Allow the user to change the order of the shapes in a compartment
From Fabio: In a compartment the order of the shapes currently always is the order in which they were added. It would be useful to allow users to change this order. E.g. you start with
Class: MyClass
- PropertyOne
- PropertyTwo
Now the user wants to switch this properties in a different way (PropertyTwo before PropertyOne)
MyClass
- PropertyTwo
- PropertyOne
- stakeholder: Diagram editor user
- keywords: Type:Enhancement, Compartments, Spray DSL, Shapes DSL, Generated diagram editor, Component: Code generator
- status: READY

## issue0199 (FunctionalRequirement)
Class cast exception in style DSL
- stakeholder: Diagram editor user
- keywords: Priority: Medium, Type: Defect, Component: Language, Styles DSL, Component: UI
- status: DONE

## issue0200 (FunctionalRequirement)
Fix outline views
- stakeholder: Diagram editor creator
- keywords: Type: Task, Component: UI, Component: Language, Shapes DSL, Styles DSL, Spray DSL
- status: DONE

## issue0201 (FunctionalRequirement)
Constant generated with white spaces
- stakeholder: Diagram editor creator
- keywords: Priority: Low, Type: Defect, Spray DSL, Component: Code generator
- status: DONE

## issue0202 (FunctionalRequirement)
Write automated tests for the generated diagram editors
There are currently some bugs in the generated diagram editors that should be disovered inside the automated build.
I have checked in some example diagram projects done with our example DSL projects:
* http://code.google.com/a/eclipselabs.org/p/spray/source/browse/examples/bpmn2.0/org.eclipselabs.spray.examples.bpmn.diagrams
* http://code.google.com/a/eclipselabs.org/p/spray/source/browse/examples/fowlerdsl/org.eclipse.xtext.example.fowlerdsl.diagrams
* http://code.google.com/a/eclipselabs.org/p/spray/source/browse/examples/fowlerdsl/org.eclipse.xtext.example.fowlerdsl.diagrams
* http://code.google.com/a/eclipselabs.org/p/spray/source/browse/examples/lwc2012/org.eclipselabs.spray.examples.lwc2012.diagrams
* http://code.google.com/a/eclipselabs.org/p/spray/source/browse/examples/one/org.eclipselabs.spray.examples.one.diagrams
* http://code.google.com/a/eclipselabs.org/p/spray/source/browse/examples/petrinet/org.eclipselabs.spray.examples.petrinet.diagrams
For how to test, see the following resources:
Graphiti Dark Feature Processing
* http://help.eclipse.org/juno/index.jsp?topic=%2Forg.eclipse.graphiti.doc%2Fresources%2Fdocu%2Fgfw%2Fdark-feature-processing.htm
* http://5ise.quanxinquanyi.de/2012/08/06/testing-graphiti-applications-with-dark-feature-processing/
Graphiti SWTBot Tests
* http://git.eclipse.org/c/gmp/org.eclipse.gmp.graphiti.git/tree/tests/org.eclipse.graphiti.bot.tests
* I (Joerg) actually developed some Graphiti SWTBot tests to, I should make the generic factored out super/helper classes available to Spray
See also the already existing SWTBot test for the Spray wizard (that currently fails)
* http://code.google.com/a/eclipselabs.org/p/spray/issues/detail?id=8
* http://code.google.com/a/eclipselabs.org/p/spray/source/browse/tests/org.eclipselabs.spray.examples.one.tests/pom.xml
The tests should be part of the example project builds: After having build the diagram DSL project an Eclipse instance should be started with the just build diagram DSL plug-in and creating a new diagram, adding and updating shapes should be tested either as SWTBot tests or dark feature processing tests.
For test concepts see here:
https://spray.ci.cloudbees.com/job/spray-docs-build/lastSuccessfulBuild/artifact/docs/org.eclipselabs.spray.doc.dev/docs/html/SprayDeveloperGuide.html#TestingthegeneratedGraphitieditor
- stakeholder: Spray developer
- keywords: Type: Task, Component: Test, Component: Code generator
- status: OPEN

## issue0203 (FunctionalRequirement)
Drag and drop of shapes only takes the top shape
- stakeholder: Diagram editor user
- keywords: Priority: Medium, Type: Defect, Component: Code generator, Generated diagram editor
- status: DONE

## issue0204 (FunctionalRequirement)
Default implementation for associating EObjects to associations
I just tested this a week ago, there seem to be no EObjects linked with connections so they appear as red dotted lines:
http://spray.eclipselabs.org.codespot.com/git/examples/bpmn2.0/org.eclipselabs.spray.examples.bpmn.diagrams/receipt/receipt.PNG
- stakeholder: Diagram editor user
- keywords: Priority: Medium, Type: Defect, Component: Code generator, Generated diagram editor
- status: READY

## issue0205 (FunctionalRequirement)
Resize of shapes containing texts ugly
Also experienced one week ago, when resizing a shape containing a text, e.g. dragging the right edge of the shape more and more to the right, the text wanders torwards the right edge until it disappears.
http://spray.eclipselabs.org.codespot.com/git/examples/bpmn2.0/org.eclipselabs.spray.examples.bpmn.diagrams/receipt/receipt.PNG
Jos' answer: I see, the horizontal-align=center of the text is taken in relationship with the text object, not in relation with the parent rectangle. And the text size grows shrinks with the text, which it should not.
- stakeholder: Diagram editor user
- keywords: Priority: Medium, Type: Defect, Component: Code generator, Generated diagram editor
- status: READY

## issue0206 (FunctionalRequirement)
Referenced gradient leads to shape generator abort
style
style MyDefaultStyle {
description = "The default style of the graphiti diagram type."
transparency = 1.00
// background-color = black
line-color = black
line-style = solid
line-width = 1
font-color = black
font-name = "Tahoma"
font-size = 12
font-bold = yes
}
style EntryStyle extends MyDefaultStyle {
background-color = EntryGradient
gradient-orientation = vertical
}
gradient EntryGradient {
area (color = red, offset = 0.0)
area (color = white, offset = 1.0)
}
gradient LoopGradient {
area (color = green, offset = 0.0)
area (color = white, offset = 1.0)
}
shape
shape EntryFigure {
ellipse {
position (x=0, y=0)
size (width=50, height=50)
style (background-color=black)
ellipse {
style (
background-color = EntryGradient
gradient-orientation = vertical
)
position (x=2, y=2)
size (width=46, height=46)
}
}
}
Shape Generator aborts.
Jos' answer: Found the problem. Gradient as backgropund color needs to be treated differently from other colors. In the Styles DSL this is done correctly, need to do it the same way in the shapes DSL.
- stakeholder: Diagram editor creator
- keywords: Priority: Medium, Type: Defect, Component: Code generator, Shapes DSL, Styles DSL
- status: IN_PROGRESS

## issue0207 (FunctionalRequirement)
Non compiling code for some shapes using polygons
- stakeholder: Diagram editor creator
- keywords: Priority: Medium, Type: Defect, Component: Code generator, Shapes DSL
- status: DONE

## issue0208 (FunctionalRequirement)
The textid and compartment id in the Spray DSl should be checked
- stakeholder: Diagram editor creator
- keywords: Type: Task, Component: Language, Spray DSL, Validation
- status: DONE

## issue0209 (FunctionalRequirement)
References to domain model ecore works only after workspace restart
- stakeholder: Diagram editor creator
- keywords: Priority: Medium, Type: Defect, Component: Language, Spray DSL, Component: UI
- status: DONE

## issue0210 (FunctionalRequirement)
Reference to gradient in DSL is not proposed
- stakeholder: Diagram editor creator
- keywords: Priority: Medium, Type: Defect, Component: Language, Styles DSL
- status: DONE

## issue0211 (FunctionalRequirement)
Propose block to bind parameters to shape definition
- stakeholder: Diagram editor creator
- keywords: Priority: Medium, Type: Defect, Component: Language, Spray DSL, Component: UI, Usability
- status: DONE

## issue0212 (QualityRequirement)
Wrong default style is generated when there are multiple Spray projects
- stakeholder: Diagram editor creator
- keywords: Priority: Medium, Type: Defect, Component: Code generator
- status: DONE

## issue0213 (FunctionalRequirement)
No or not interpreted property for gradient package name
- stakeholder: Diagram editor creator
- keywords: Priority: Medium, Type: Defect, Component: Code generator
- status: DONE

## issue0214 (FunctionalRequirement)
Do not create [dsl_name].properties file anymore
- stakeholder: Diagram editor creator
- keywords: Priority: Medium, Type: Defect, Backward compatibility, Component: Code generator, Component: UI, Properties file
- status: DONE

## issue0215 (FunctionalRequirement)
Discover colliding imports
Giving a referenced shape the same name as used for the referenced domain model object will result in a conflicting import, where the a class with the same simple name is tried to imported from different packages. Such conflict may occur also in other situations.
class Transition {
connection Transition {
name into connectionText
// event.name into connectionText
// fromState.name into fromText
// toState.name into toText
}
The generator should discover such conflicts and should use for one class the import and for the other class full qualified access. A matter of the Spray import manager.
- stakeholder: Diagram editor creator
- keywords: Priority: Low, Type: Defect, Component: Code generator
- status: OPEN

## issue0216 (FunctionalRequirement)
Duplicate entries in generated properties view
see the appended screenshot for an example. The name feature appears twice. I guess this is because the direct properties as well as the inherited properties of the current class are merged with the properties within its superclass hierarchy: http://spray.eclipselabs.org.codespot.com/issues/attachment?aid=2160000000&name=fowlerdsl.png&token=_S-X7jrZjZTmqJ1SIhnSdGO_Ymw%3A1364587972852&inline=1&thumb=1
- stakeholder: Diagram editor user
- keywords: Priority: Medium, Type: Defect, Generated diagram editor, Component: Code generator, Properties view
- status: OPEN

## issue0217 (FunctionalRequirement)
Better handling of text size
Currently you're forced to give position, width/height and id inside a text definition otherwise you end up with a strange error message:
rule ruleCommonLayout failed predicate:
{getUnorderedGroupHelper().canLeave(grammarAccess.getCommonLayoutAccess().getUnorderedGroup_1())}?
text {
position (x=0, y=0)
size (width=20, height=10)
id = fromText
}
Width and height are dependent on the text style (font, font size, character spacing, ...)
So defining a text size has only an effect if the font size defined by the style is lower or equal to the stated size (visible when backgound-color is not set to transparent) otherwise the for style calculated size is applied and in consequence the text representation is cut of at the boundaries of the container holding the text.
- stakeholder: Diagram editor user
- keywords: Priority: Low, Type: Defect, Component: Code generator, Generated diagram editor
- status: OPEN

## issue0218 (FunctionalRequirement)
ClassCastException StyleScopeProvider cannot be cast to XbaseScopeProvider
- stakeholder: Diagram editor creator
- keywords: Priority: Medium, Type: Defect, Component: Language, Styles DSL
- status: DONE

## issue0219 (FunctionalRequirement)
Browse workspace in new project wizard does not work
- stakeholder: Diagram editor creator
- keywords: Priority: Medium, Type: Defect, Spray project wizard
- status: DONE

## issue0220 (FunctionalRequirement)
Migrate org.eclipselabs.spray:org.eclipselabs.spray.xtext.tests
The tests in org.eclipselabs.spray:org.eclipselabs.spray.xtext.tests are still based on using containers inside Spray DSL. This have to be changed to reference shapes form shape DSL files.
So the test setup have to be changed in a way that shapes and styles are resolved as valid EMF resources.
- stakeholder: Spray developer
- keywords: Type: Task, Component: Test, Component: Code generator
- status: OPEN

## issue0221 (FunctionalRequirement)
Migrate org.eclipselabs.spray.shapes.tests
- stakeholder: Spray developer
- keywords: Type: Task, Component: Test, Component: Code generator, Shapes DSL
- status: DONE

## issue0222 (FunctionalRequirement)
Review org.eclipselabs.spray:org.eclipselabs.spray.generator.graphiti.tests
The tests for asserting the expected for the Spray generator are themselves generated now.
The test assertions have to be checked against the actual produced generated code at runtime to verify that there are no differences due to not resolved shapes/styles/genmodels or other influences.
This check might be done by comparing the actual generated code (to be copied inside the test project) with the code fragments to be generated as assertions (actually the generation approach has been chosen to avoid platform dependent differences in line break characters).
There also some issues with generated code assertions because of trailing empty lines inside the generated code.
When the generated test cases are verified add test case generators for the other example projects.
- stakeholder: Spray developer
- keywords: Type: Task, Component: Test, Component: Code generator
- status: OPEN

## issue0223 (FunctionalRequirement)
Regenerate and implement test cases on platform level for example Spray projects
There has been unit test case stubs pregenerated for the example one Spray project (a test class for each generated class (e.g. add feature, update feature and so on was generated). These has been removed as they were no longer valid for the now generated code.
Regenerate those test case stubs for the new generated code basis AND check if it is feasible to implement valid unit tests (maybe with some mocking) on top of them.
- stakeholder: Spray developer
- keywords: Type: Task, Component: Test, Component: Code generator
- status: OPEN

## issue0224 (FunctionalRequirement)
Editing .shape file results in opening the generated .svg file
- stakeholder: Diagram editor creator
- keywords: Priority: Medium, Type: Defect, Shapes DSL, Component: Language, Component: UI
- status: DONE

## issue0225 (FunctionalRequirement)
Activator is invalid/not found in runtime Eclipse
- stakeholder: Diagram editor creator
- keywords: Priority: Medium, Type: Defect, Component: Build, Backward compatibility
- status: DONE

## issue0226 (FunctionalRequirement)
Add EMF SDK to Spray 3rd party update site
- stakeholder: Diagram editor creator
- keywords: Type: Task, Component: Build
- status: DONE

## issue0227 (FunctionalRequirement)
Update Spray completion templates to not include container node anymore
- stakeholder: Diagram editor creator
- keywords: Priority: Medium, Type: Defect, Component: Language, Spray DSL, Component: UI
- status: DONE

## issue0228 (FunctionalRequirement)
Update project template to do not use removed container nodes
- stakeholder: Diagram editor creator
- keywords: Priority: Medium, Type: Defect, Component: Code generator, Spray DSL
- status: DONE

## issue0229 (FunctionalRequirement)
No proposal after alias
- stakeholder: Diagram editor creator
- keywords: Priority: Medium, Type: Defect, Component: UI, Component: Language
- status: DONE

## issue0230 (FunctionalRequirement)
Inner compartment does not fill its container
- stakeholder: Diagram editor user
- keywords: Priority: Medium, Type: Defect, Component: Code generator, Compartments, Generated diagram editor
- status: DONE

## issue0231 (FunctionalRequirement)
Initial creation of or change in of EMF domain model project not recognized in Spray project
- stakeholder: Diagram editor creator
- keywords: Priority: Medium, Type: Defect, Spray DSL, Component: UI
- status: DONE

## issue0232 (QualityRequirement)
Provide quickfixes for shape and style definitions
- keywords: Type: Enhancement, Component: Language, Spray DSL, Shapes DSL, Component: UI, Usability
- status: DONE

## issue0233 (FunctionalRequirement)
Allow to pass constant values to referenced shape
Currently it is only possible to pass values to a referenced shape in by referencing a feature of the domain model:
class ActionBlock alias Action {
shape ActionBlockShape {
actionName into action
}
behavior {
create palette "Elements"
}
}
shape ActionBlockShape {
stretching(horizontal=true,vertical=true)
rectangle {
position(x=0,y=0)
size(width=100,height=100)
text {
position(x=5,y=5)
size(width=90,height=90)
id = action
}
}
}
So in the example actionName must be a feature of ActionBlock.
class ActionBlock alias Action {
shape ActionBlockShape {
actionName into action
}
As workaround you can write:
class ActionBlock alias Action {
shape ActionBlockShape {
actionName into action ("Constant text")
}
But you still need an existing feature of the domain model element.
What you actually want to write is:
class ActionBlock alias Action {
shape ActionBlockShape {
"Constant text" into action
}
Or even more constant direct in shape:
shape ActionBlockShape {
stretching(horizontal=true,vertical=true)
rectangle {
position(x=0,y=0)
size(width=100,height=100)
text {
position(x=5,y=5)
size(width=90,height=90)
id = "Constant text"
}
}
}
(The last version is actually a separate issue).
before:
shape UniqueRuleShape {
name into uniqueRuleName ( "Rule: " + name )
reference properties into properties
}
Now it is additional possible to write
shape UniqueRuleShape {
constant "Rule" + name into uniqueRuleName
reference properties into properties
}
And with the last syntax you can leave out the feature:
shape UniqueRuleShape {
constant "Rule" into uniqueRuleName
reference properties into properties
}
We should consider to deprecate the bracket syntax so we can leave out the keyword 'constant':
shape UniqueRuleShape {
"Rule" + name into uniqueRuleName
reference properties into properties
}
The constant syntax does not work as described here:
http://groups.google.com/group/spray-users/msg/3c2c7c962bbd5951
Reason is, that the EMF feature was used for generating the DirectEditingFeature. That does not work anymore when with 'constant "Rule" into uniqueRuleName' no feature is set. So as workaround constant name into uniqueRuleName ( "Rule" ) is currently only possible.
- stakeholder: Diagram editor creator
- keywords: Priority: Medium, Type: Defect
- status: IN_PROGRESS

## issue0234 (FunctionalRequirement)
Containment element got lost
- stakeholder: Diagram editor user
- keywords: Priority: Medium, Type: Defect, Component: Code generator, Generated diagram editor
- status: DONE

## issue0235 (FunctionalRequirement)
Support compartments also for connections
See http://groups.google.com/group/spray-users/browse_thread/thread/8f3b10ebfcbcea29
Could be useful when connection labels should be dependent on the containment hierarchy.
- stakeholder: Diagram editor creator
- keywords: Priority: Medium, Type: Enhancement, Compartments
- status: OPEN

## issue0236 (FunctionalRequirement)
Problems with properties view when using compartments
- stakeholder: Diagram editor user
- keywords: Priority: Medium, Type: Defect, Component: Code generator, Generated diagram editor, Properties view
- status: DONE

## issue0237 (FunctionalRequirement)
Make Spray working in Eclipse Kepler (4.3)
- stakeholder: Spray developer
- keywords: Priority: Low, Type: Task, Component: Build
- status: IN_PROGRESS

## issue0238 (FunctionalRequirement)
overridingGuiceModule.exsd not exported
- stakeholder: Diagram editor creator
- keywords: Priority: Medium, Type: Defect, Component: Build
- status: DONE

## issue0239 (FunctionalRequirement)
produce diagram elements manually
it would be very nice of one could invoke diagram elements like connections and businessmodels manually in order to parse a file which should be represented as a spray diagram
- stakeholder: Diagram editor creator
- keywords: Priority: Medium, Type: Enhancement, Shapes DSL, Interpreter
- status: OPEN

## issue0240 (FunctionalRequirement)
Spray projects in one workspace mess each other up
I updated Spray last week from here https://spray.ci.cloudbees.com/job/spray-assembly-build/lastSuccessfulBuild/artifact/releng/org.eclipselabs.spray.updatesite/target/repository/
My previous version dated back to September 2012. After I fixed some syntax problems (You really need to update the user documentation) the following thing happened.
What steps will reproduce the problem?
1. I have a spray project a.b.c.mydiagram based on a.b.c.mydiagram.model
2. I create a second spray project in the same workspace a.b.c.mydiagram_newSpray based on the same model
3. In the first project a.b.c.mydiagram I make some change in mydiagram.spray and code is generated again.
What is the expected output?
I expect small cosmetic changes to the source files
What do you see instead?
all files are generated under the package a.b.c.mydiagram_newSpray (still in the correct project). And ofcourse all old files from a.b.c.mydiagram are removed.
If I create yet another project with some other name, and change the first project, the naming of the third project is used.
What version of the product are you using? On what operating system?
I am using Eclipse Juno x64 with Graphiti 0.10 and Spray updated last Tuesday the 12th Feb. on Windows 7 Pro x64
Joerg's answer: Please note that we did some changes how configuration is loaded and applied. So configuration is now expected to be in a file named spray.properties, this file was named differently before. That spray.properties is created when creating a new Spray project. So when you open your the spray file of your old project with the Spray editor of the current version an empty spray.properties file is generated as fall back. The empty spray.properties file is causing this strange behavior. This shall be handled. As work around you have to copy the content of the old properties file into the new one.
- stakeholder: Diagram editor creator
- keywords: Priority: Medium, Type: Defect, Backward compatibility, Component: UI
- status: READY

## issue0241 (FunctionalRequirement)
Fix problems with update feature for connections
see http://groups.google.com/group/spray-users/browse_thread/thread/743290420ddc93cf, duplicate of issue 204?
- stakeholder: Diagram editor user
- keywords: Priority: Medium, Type: Defect, Generated diagram editor
- status: OPEN

## issue0242 (FunctionalRequirement)
Allow resizing of compartments with non-xy-layout
Resizing of compartments with vertical resp. horizontal layout is currently not supported. Only by resizing one of its contained elements the size of the compartment is changable (as it is then recalculated for the compartment). The other way round would mean that there should exist a strategy that transforms a resize request at the compartment to resize requests to its contained elements (still with respect to layout manager).
See: http://groups.google.com/group/spray-users/browse_thread/thread/743290420ddc93cf
- stakeholder: Diagram editor user
- keywords: Priority: Low, Type: Enhancement, Compartments, Component: Code generator, Generated diagram editor
- status: OPEN

## issue0243 (FunctionalRequirement)
Import Package missing in generated Spray MANIFEST
- stakeholder: Diagram editor user
- keywords: Operating System: All, Priority: High, Type: Defect, Component: Code generator
- status: DONE

## issue0244 (FunctionalRequirement)
plugin.xml just in src-gen
What steps will reproduce the problem?
1. Create a new Spray project (following steps in the 5 minutes tutorial)
2. Wait for generation of diagram
What is the expected output? What do you see instead?
The plugin.xml file is generated in the project folder (at least at the first time). But the plugin.xml appears just in the src-gen folder.
--> will be fixed in conjunction with issue #89
- stakeholder: Diagram editor user
- keywords: Priority: Medium, Type: Defect, Component: Code generator
- status: READY

## issue0245 (FunctionalRequirement)
reference section in metaclass
What steps will reproduce the problem?
1. Run Spray-Runtime
2. Import archive file in workspace
3. Open petrinet.spray
4. Try the content assist before "targetTransitions" or "targetPlaces"
What is the expected output? What do you see instead?
A context menu opens with a content assist.
No content assist at all shows up!
- stakeholder: Diagram editor user
- keywords: Priority: Medium, Type: Defect, Component: Language, Spray DSL, Component: UI
- status: DONE

## issue0246 (FunctionalRequirement)
No connection shape on reference section
What steps will reproduce the problem?
1. Run Spray-Runtime
2. Import archive file in workspace (example archive file can be found on issue 245)
3. Open petrinet.shape
4. Create a connection shape
5. Open petrinet.spray
6. Add the created connection shape after the connection keyword in the line beginning with "targetTransitions" or "targetPlaces"
What is the expected output? What do you see instead?
Expected: The generated "AddReferenceFeature" fetches the defined shape.
But, following code will generated (just a free form connection)
public PictogramElement add(final IAddContext context) {
final IAddConnectionContext addConContext = (IAddConnectionContext) context;
Place addedDomainObject = (Place) context.getNewObject();
// CONNECTION WITH POLYLINE
final Connection connection = peCreateService.createFreeFormConnection(getDiagram());
connection.setStart(addConContext.getSourceAnchor());
connection.setEnd(addConContext.getTargetAnchor());
- stakeholder: Diagram editor user
- keywords: Priority: Medium, Type-Defect, Component: Code generator, Shapes DSL, Spray DSL
- status: OPEN

## issue0247 (FunctionalRequirement)
Compartment in Rectangle with Superclass
Hi together,
I want to visualize for example a webpage with a lot of controls in graphiti spray. I create a ecore-model with Tab, this tab contains pages (= container) which contains a lot of widgets (Labels, Buttons, etc.).
The question is why I can't reference a superclass (=widget) for the container to the buttons or labels. This will not showing in the Toolbar and the code-generating getting error in SprayToolBehaviorProvider (because of not generating the class).
I attach the ecore-model und spray shapes files. Can you tell me how to do this with the superclass, or should I separatly references all widgets to container like pages?
The other question is, is it the right way to visualizate if I use a class (in the image it is SketchDomainModel) that reference to all classes in ecore.
Thanks for helping.
Greez Dowbar
What version of the product are you using? On what operating system?: 0.5.0
Please provide any additional information below: Eclipse Juno 4.2.2
Another question is, if I want to use the widget in the toolbar the "SketchDomainModel"-Class should known all the widget class in ecore, is it?
Answer Joerg Reichert:
Hi Dowbar,
you can actually structure your domain model this way:
SketchDomainModel
* tabs : Tab [0..*]
* pages : Page [0..*]
* widgets : Widget [0..*]
* subWidgets : Widget [0..*]
* Toolbar extends Widget
* Button extends Widget
In Spray you define the mapping this way:
diagram spray for SketchDomainModel style SprayDefaultStyle
class Tab icon "ecore/EClass.gif" {
shape TabShape {
reference pages into tabCompartment
}
behavior {
create into tabs palette "Container";
}
}
class Page icon "ecore/EClass.gif" {
shape PageShape {
reference widgets into pageCompartment
}
behavior {
create palette "Container";
}
}
class Toolbar icon "ecore/EClass.gif" {
shape ToolbarShape {
reference subWidgets into toolbarCompartment
}
behavior {
create palette "Widget";
}
}
class Button icon "ecore/EClass.gif" {
shape ButtonShape {
name into buttonID
}
behavior {
create palette "Widget";
}
}
You see, you only have to leave off the "into ..." part. Adding a button to a toolbar inside the diagram will add the button domain object to the subWidgets of the toolbar domain object as the mapping definition for Toolbar states "reference subWidgets into ...".
Best regards,
Joerg
- keywords: Priority: Medium, Type: Defect, Component: Language, Compartments, Spray DSL
- status: DONE

## issue0248 (FunctionalRequirement)
Styling Text
Hello,
I created a Shape with a text and the text I want to style with transparency and setting a font-color. But no changes will do if I try it. What is the issue for this siutation.
If I setup the BackgroundColor of this Text, it works fine. Seems not all attributes of styling works.
Here my exmaple code.
shape TabShape {
stretching(horizontal=false, vertical=false)
rectangle style TabStyle {
compartment (
id = tabCompartment
layout = fixed
spacing=2
margin=2
)
position (x=0, y=20)
size (width=600, height=400)
style (background-color=RGB (192, 192, 192))
}
text{
align(horizontal=center,vertical=middle)
position(x=0, y=0)
size(width=600,height=20)
style(background-color=blue font-color=red transparency=0.1)
id=tabID
}
}
Thanks a lot for regarding.
Greez
dowbar
Answer Joerg Reichert:
Reproduced, only
element_2.setBackground(gaService.manageColor(diagram, new ColorConstant(192, 192, 192)));
is generated inside TabShape.java although font-color has been specified in Shape DSL file.
As workaround you can put the other style information pieces inside the TabStyle that is referenced at the rectangle. This will be then applied to the contained text, too, as the styles are applied to all contained elements, see generated TabShape.java:
ISprayStyle style_2 = new sketch.diagram.styles.TabStyle();
element_2.setStyle(style_2.getStyle(diagram));
gaService.setLocationAndSize(element_2, 0, 20, 600, 400);
SprayLayoutService.setLayoutData(shape_2, 600, 400, true);
element_2.setBackground(gaService.manageColor(diagram, new ColorConstant(192, 192, 192)));
- keywords: Priority: Low, Type: Defect, Component: Code generator, Shapes DSL
- status: READY

## issue0249 (FunctionalRequirement)
Shape preview in hover under Ubuntu is not visible
- status: OPEN

## issue0250 (FunctionalRequirement)
Provide project wizards to create example projects
- status: OPEN

## issue0251 (FunctionalRequirement)
Provide overview picture of plug-in project structure in developer guide
- status: OPEN

## issue0252 (FunctionalRequirement)
Clean up preference tree
- status: OPEN

## issue0253 (FunctionalRequirement)
Provide file wizards for creating new Style, Shape and Spray files
- status: OPEN

## issue0254 (FunctionalRequirement)
Export Spray Project
- status: OPEN

## issue0255 (FunctionalRequirement)
Update to Xtext and Xtend 2.4.0
- status: OPEN

## issue0256 (FunctionalRequirement)
Spray generator produce invalid method calls when referenced EMF attribute starts with 'is'
- status: OPEN

## issue0257 (FunctionalRequirement)
Using compartment in rounded-rectangle
- status: OPEN

## issue0258 (FunctionalRequirement)
Shape value to EMF model
- status: OPEN

## issue0259 (FunctionalRequirement)
Genmodel can not be found on Git projects
- status: OPEN

## issue0260 (FunctionalRequirement)
Discover and handle colliding imports
- status: OPEN

## issue0261 (FunctionalRequirement)
Code generator uses hard coded paths (src, src-gen) in some places
- status: OPEN

## issue0262 (FunctionalRequirement)
Remove calls of API marked as deprecated
- status: OPEN

## issue0263 (FunctionalRequirement)
Quick fix applied to file in wrong project
- status: OPEN

## issue0264 (FunctionalRequirement)
Shapes and Styles generated code with smaller overridable methods
- status: OPEN

## issue0265 (FunctionalRequirement)
Change color of Shape
- status: OPEN

## issue0266 (FunctionalRequirement)
Allow adding anchor shapes at runtime (special case of compartment)
- status: OPEN

## issue0267 (FunctionalRequirement)
Naming-Problem on Imported and Domain-Model Classes
- status: OPEN

## issue0268 (FunctionalRequirement)
New shape class name scheme not applied to inner connection references
- status: OPEN
