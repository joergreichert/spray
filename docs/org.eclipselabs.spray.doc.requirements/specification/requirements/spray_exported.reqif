# Spray Exported

# Specification
- name: org.eclipselabs.spray.requirements.issues_neu
- description: This package contains all requirements grabbed in the Spray Google Code issues: http://code.google.com/a/eclipselabs.org/p/spray/issues/list

## issue0001
Patch for /wiki/Spray_DSL_Ideas.wiki
29.05.2011 20:51:53 (andreas.x.graf): Additional Ideas
01.09.2011 14:49:37 (karsten.thoms): Applied
01.09.2011 14:49:53 (karsten.thoms):
- stakeholder: Spray developer
- keywords: Type: Patch
- status: DONE

## issue0002
There is a path hard coded in JavaGenFile.java.
29.08.2011 17:56:14 (joswarmer): There is a path hard coded in JavaGenFile.java. All hardcoded paths should be removed. (Issue sent by email by Jorg Reichert)
30.08.2011 11:56:52 (joswarmer):
- stakeholder: Spray developer
- keywords: Type: Defect, Priority: Medium
- status: DONE

## issue0003
Downgrade version to 0.1.0
01.09.2011 16:32:38 (karsten.thoms): The plugins have currently version 1.0.0 (without qualifier).
Since this is early state development the versions of the plugins should be set to 0.1.0.qualifier resp. 0.1.0-SNAPSHOT in the pom.xml files.
01.09.2011 16:34:56 (karsten.thoms): Dependencies in the manifest files must be updated, too, of course.
01.09.2011 21:56:07 (karsten.thoms): Done
- stakeholder: Spray developer
- keywords: Type: Defect, Priority: Medium
- status: DONE

## issue0004
Add feature projects
01.09.2011 16:54:51 (karsten.thoms): Add feature projects:
- org.xspray.feature
- org.xspray.feature.source
01.09.2011 16:55:16 (karsten.thoms):
01.09.2011 17:10:47 (karsten.thoms): Also add
- org.xspray.feature.sdk
which holds both feature above plus the examples and tests and their sources.
01.09.2011 21:56:27 (karsten.thoms): Done
- stakeholder: Spray developer
- keywords: Type: Task, Priority: Medium
- status: DONE

## issue0005
Add Maven POMs
01.09.2011 17:12:39 (karsten.thoms): Add Maven POMs to each project and provide a master POM.
The master POM should be in the /releng folder.
01.09.2011 21:56:39 (karsten.thoms): Done
28.10.2011 13:12:42 (karsten.thoms): This issue was closed by revision df2a900a8211.
- stakeholder: Spray developer
- keywords: Type: Task, Priority: Medium
- status: DONE

## issue0006
Use real cross-references for rule MetaClass
01.09.2011 23:54:03 (karsten.thoms): Currently the metaclass name is just an named reference, no real cross reference.
Rule &quot;MetaClass&quot; must be changed from:
{{{
MetaClass :
'class' name=ID ('alias' alias=ID)? ('icon' icon=STRING)?
}}}
to:
{{{
MetaClass :
'class' name=[ecore::EClass|QualifiedName] ('alias' alias=ID)? ('icon' icon=STRING)?
}}}
01.09.2011 23:54:36 (karsten.thoms):
09.09.2011 00:12:34 (karsten.thoms):
09.09.2011 01:22:56 (karsten.thoms): Done.
Spray uses now cross-references to the EClasses referred to by the 'class' concept. The DSL itself does not change much, but the implementation did change significantly.
- stakeholder: Spray user
- keywords: Type: Defect, Priority: Medium
- status: DONE

## issue0007
Enable referencing of IColorConstant instances as color
02.09.2011 15:06:38 (karsten.thoms): Spray uses an enum to define colors. The generator maps that to IColorConstants. The Spray DSL should directly refer to a JvmType and filter them by type IColorConstant.
{{{
...
lineColor = Color
...
enum Color :
BLACK = 'black'
}}}
Change to:
{{{
Color : type = JvmTypeReference
}}}
Later this should be extended to compute the color by an Xbase expression.
21.09.2011 23:02:32 (karsten.thoms): Colors from IColorConstant can be referred by their lower-case simple name ('black'), all others can be referred to by qualified field name (IColorConstant::BLACK)
This is configurable in principle, depending on the runtime implementation. A runtime must therefore implement IColorConstantTypeProvider.
User Guide:
http://code.google.com/a/eclipselabs.org/p/spray/wiki/UserGuide_Language_Layout
- stakeholder: Spray user
- keywords: Type: Defect, Priority: Medium
- status: DONE

## issue0008
Provide working SWTBot Tests for the example project
02.09.2011 16:19:49 (de.abg.reichert.joerg): The SWTBot tests as black box tests should ensure, that the generated example diagram code provides the expected behavior. This should make the developers confident, that changes to the DSL and the associated generator, that break the expected behavior, are discovered soon.
Beside the SWTBot tests there can be implemented simple unit tests for single features, too. This would require a lot of mocking interacting classes, but with those tests, causes of misbehavior can be spotted more easily. Here also the dark feature processing is needed: http://help.eclipse.org/indigo/topic/org.eclipse.graphiti.doc/resources/docu/gfw/dark-feature-processing.htm
How to run SWTBot headless in Maven is described here: http://wiki.eclipse.org/SWTBot/Maven
Take the example tests contained in Graphiti source code as reference:
PSF for CVS or better http://git.eclipse.org/c/gmp/org.eclipse.gmp.graphiti.git/
&lt;?xml version=&quot;1.0&quot; encoding=&quot;UTF-8&quot;?&gt;
&lt;psf version=&quot;2.0&quot;&gt;
&lt;provider id=&quot;org.eclipse.team.cvs.core.cvsnature&quot;&gt;
&lt;project reference=&quot;1.0,:pserver:dev.eclipse.org:/cvsroot/modeling,org.eclipse.gmp/org.eclipse.gmp.graphiti/tests/org.eclipse.graphiti.bot.tests,org.eclipse.graphiti.bot.tests&quot;/&gt;
&lt;project reference=&quot;1.0,:pserver:dev.eclipse.org:/cvsroot/modeling,org.eclipse.gmp/org.eclipse.gmp.graphiti/tests/org.eclipse.graphiti.tests,org.eclipse.graphiti.tests&quot;/&gt;
&lt;project reference=&quot;1.0,:pserver:dev.eclipse.org:/cvsroot/modeling,org.eclipse.gmp/org.eclipse.gmp.graphiti/features/org.eclipse.graphiti.tests-feature,org.eclipse.graphiti.tests-feature&quot;/&gt;
&lt;project reference=&quot;1.0,:pserver:dev.eclipse.org:/cvsroot/modeling,org.eclipse.gmp/org.eclipse.gmp.graphiti/tests/org.eclipse.graphiti.testtool.ecore,org.eclipse.graphiti.testtool.ecore&quot;/&gt;
&lt;project reference=&quot;1.0,:pserver:dev.eclipse.org:/cvsroot/modeling,org.eclipse.gmp/org.eclipse.gmp.graphiti/tests/org.eclipse.graphiti.testtool.sketch,org.eclipse.graphiti.testtool.sketch&quot;/&gt;
&lt;project reference=&quot;1.0,:pserver:dev.eclipse.org:/cvsroot/modeling,org.eclipse.gmp/org.eclipse.gmp.graphiti/tests/org.eclipse.graphiti.ui.tests,org.eclipse.graphiti.ui.tests&quot;/&gt;
&lt;/provider&gt;
&lt;/psf&gt;
02.09.2011 16:24:42 (karsten.thoms): If the first SWT Bot tests are available, I will enable them in the build.
13.09.2011 08:59:24 (karsten.thoms): Found useful post here: http://dev.eclipse.org/mhonarc/lists/tycho-user/msg00466.html
13.09.2011 09:34:25 (karsten.thoms):
13.09.2011 14:39:00 (project.spray): Execution of the SWT Bot tests are now included in the build.
For the CI Build they are disabled (by activating profile "skip-ui-tests".
09.11.2011 14:25:27 (de.abg.reichert.joerg): Currently the example one example SWTBot Test is very fragile. It works only on certain machines, sometimes if cannot found actual visible elements in the dialog and thus abort and so on.
Some problems may fix with more use of async access blocks and sleeps. But if this is enough, one should consider evaluating one of these tools instead:
* http://code.google.com/intl/de-DE/javadevtools/wintester/html/index.html
* http://www.eclipse.org/jubula/
The testing of UI is still very important as some problems only occur in a running Eclipse (ok, some of these issues may be covered by Simple JUnit plug-in tests). The UI test tool to choose, should produce predictable results and should be able to test GEF based stuff.
13.04.2012 11:32:48 (de.abg.reichert.joerg): There is a test case for the default use of the Spray wizard to create a new Spray project, then inserting the custom Spray Xtext definition and then running the generator:
http://code.google.com/a/eclipselabs.org/p/spray/source/browse/tests/org.eclipselabs.spray.examples.one.tests/src/org/eclipselabs/spray/examples/one/tests/WizardTest.java
There is still lot to do, e.g. currently there is no validation of the results of the UI test, the special cases are not covered yet (different configurations in the wizard, although the test infrastructure allows customization easily).
Another things, that a Maven Tycho build is currently not able to set up a PDE/OSGi enabled Eclipse test instance, so you cannot run a UI test that creates plug-in projects that needs dependency resolving or even more to use these just created plug-in projects to start a further Eclipse instance, e.g. to check if your able to create Graphiti diagram from the generated projects.
So these test steps have to be split up:
1. Test the generation and use of the Spray diagram project
2. Test the usability of the just before generated and Spray diagram project to create a Graphiti diagram (this would be a further UI Test process using the generated Spray diagram project as plug-in dependency - so this project must be available from somewhere, e.g. from a tmp directory)
As this task is to big to track, it will splitted in smaller issues. Thus this issue will be marked as fixed in context of providing a reusable test infrastructure.
- stakeholder: Spray user
- keywords: Type: Enhancement, Priority: Medium
- status: DONE

## issue0009
Derive grammar from Xbase
02.09.2011 16:27:03 (karsten.thoms): Spray will need Xbase expressions for different aspects. The grammar must be derived from Xbase then.
Since Xbase API is currently fluent, the exact version to use should be pinned in the manifests. Currently this is 2.0.1.
21.09.2011 23:04:43 (karsten.thoms): Grammar is derived from Xbase now. Using expressions for type Text to create useful shape labels. Integrated Xbase compiler into the Xtend templates.
21.09.2011 23:05:04 (karsten.thoms):
- stakeholder: Spray user
- keywords: Type: Defect, Priority: Medium
- status: DONE

## issue0010
Include dependent artifacts into p2-repository
05.09.2011 21:37:05 (karsten.thoms): The built eclipse repository does only contain the plugins from the Spray project. When using the update site users might need to add too much update sites to get the dependent features from (SWTBot, xtext-utils,...).
The tycho-p2-repository-plugin plugin can be configured to include the dependent plugins by setting the includeAllDependencies property:
{{{
&lt;plugin&gt;
&lt;groupId&gt;org.eclipse.tycho&lt;/groupId&gt;
&lt;artifactId&gt;tycho-p2-repository-plugin&lt;/artifactId&gt;
&lt;configuration&gt;
&lt;includeAllDependencies&gt;true&lt;/includeAllDependencies&gt;
&lt;repositoryName&gt;spray-${project.version}&lt;/repositoryName&gt;
&lt;/configuration&gt;
&lt;/plugin&gt;
}}}
05.09.2011 21:37:35 (karsten.thoms): Done
- stakeholder: Spray user
- keywords: Type: Task, Priority: Medium
- status: DONE

## issue0011
Execute Xtext generator in the build
05.09.2011 21:53:31 (karsten.thoms): Currently the content of the src-gen and xtend-gen folder is checked in. It is generally a bad practice to check in generated code. However, checking in xtend-gen is currently mandatory due to limitations on compiling Xtend sources in a headless build. But the contents of src-gen can be derived.
To do:
- Configure the Fornax Workflow plugin to execute the GenerateXspray.mwe2 workflow
- Configure the maven-clean-plugin
- Remove contents of src-gen from the repository
- Add .gitignore in src-gen
05.09.2011 21:55:02 (karsten.thoms): Changed pom.xml from org.xspray.xtext
Removed src-gen content from org.xspray.xtext & org.xspray.xtext.ui
05.09.2011 21:55:24 (karsten.thoms):
- stakeholder: Spray user
- keywords: Type: Task, Priority: Medium, Component: Build
- status: DONE

## issue0012
Change the path handling so the Graphiti generator can be used inside an automated build
06.09.2011 15:06:13 (de.abg.reichert.joerg): Originally there were used absolute paths. This has been slightly improved by using relative paths now. But this mechanism will not work, when the referenced file is contained within a jar file.
examples/org.xspray.examples.one/model/mod4j-busmod.properties contains property projectPath. This is used as destination folder for the generated files.
examples/org.xspray.examples.one/model/mod4j-busmod.xspray uses the path to import the BusinessDomainDsl.ecore.
org.xspray.xtext.generator.Main from project plugins/org.xspray.xtext is launched with the path to the .xspray file as input parameter.
Using &quot;platform:/resource/ does not work, the so addressed files cannot be found this way. This might be due the fact that the projects are imported as reference in my Eclipse workspace from my local git repository.
The relative path solution assumes currently that org.xspray.xtext is current working directory from that the domain meta model resp. the target generation project can be reached that way:
../../examples/org.mod4j.dsl.businessdomain.mm/model/BusinessDomainDsl.ecore
../../examples/org.xspray.examples.one
18.10.2011 17:21:45 (joswarmer): IS this styill open ?
18.10.2011 18:07:53 (de.abg.reichert.joerg): No, I do not think so.
- stakeholder: Spray user
- keywords: Type: Defect, Priority: Medium, path, build
- status: DONE

## issue0013
Xtend: use typeof() instead of instanceof in filter
08.09.2011 22:36:30 (karsten.thoms): Several templates use 'instanceof' in the filter() function:
{{{
filter(c | c instanceof EClass)
}}}
The problem with this pattern is that the resulting list is not typed to the desired type.
If using filter with the `typeof` operator, the resulting iterable will be typed with the filtered type.
The templates must use this pattern:
{{{
filter(typeof(EClass))
}}}
09.09.2011 00:11:48 (karsten.thoms):
09.09.2011 01:23:20 (karsten.thoms): Refactored Xtend code
- stakeholder: Spray user
- keywords: Type: Defect, Priority: Medium
- status: DONE

## issue0014
Use @Inject instead of new operator in Xtend
08.09.2011 23:08:48 (karsten.thoms): In several places of the Xtend templates the 'new' operator is used to instantiate template classes and other helpers.
This is not the recommended way, it is better to inject these objects. This way, these classes can use Extensions, otherwise the classes are not managed with Guice.
Example:
`XsprayGenerator.xtend`:
{{{
var Plugin plugin = new Plugin()
}}}
Change to
{{{
class XprayGenerator ... {
@Inject Plugin plugin
}
}}}
09.09.2011 00:11:37 (karsten.thoms):
09.09.2011 00:54:32 (karsten.thoms): This issue was closed by revision d9daf3c2bb8b.
- stakeholder: Spray user
- keywords: Type: Defect, Priority: Medium, Component: Codegen
- status: DONE

## issue0015
Make generation of timestamps configurable in properties file
08.09.2011 23:52:11 (karsten.thoms): The file headers of generated files contain a timestamp
Generated on Mon Aug 29 17:53:16 CEST 2011 by XSpray
This timestamp makes it harder to compare changes in generated files, since the timestamp will always change and thus all files will be shown as changed when comparing two generator results.
This feature should be configurable, and turned off for reference examples. The proper place to configure it is the Spray generator properties file.
09.09.2011 00:11:27 (karsten.thoms):
09.09.2011 00:54:33 (karsten.thoms): This issue was closed by revision 6a0ffaf8ec60.
- stakeholder: Spray user
- keywords: Type: Enhancement, Priority: Medium
- status: DONE

## issue0016
Trigger generator on changing the properties file
09.09.2011 00:27:13 (karsten.thoms): When the generator properties file is changed the Spray generator should also be triggered. Currently this happens only when changing the .xspray file.
23.09.2011 08:07:09 (karsten.thoms): Added an IResourceChangeListener to SprayActivatorExt. The build is triggered by touching the .spray file.
I tried by invoking a build for the XtextBuilder
{{{
project.build(IncrementalProjectBuilder.FULL_BUILD, "org.eclipse.xtext.ui.shared.xtextBuilder", new HashMap<String, String>(), new NullProgressMonitor());
}}}
But this caused the generator to execute twice.
26.09.2011 12:40:09 (karsten.thoms): Added a IResourceChangeListener to SprayActivatorExt
- stakeholder: Spray user
- keywords: Type: Enhancement, Priority: Medium, Component: Codegen
- status: DONE

## issue0017
Integrate JDT Formatter
09.09.2011 00:29:09 (karsten.thoms): The JDT Formatter should be integrated to post process the generated Java files.
12.09.2011 19:22:12 (karsten.thoms): Added JDT Post processor to the .generator package.
Extended and injected JavaIoFileSystemAccess and EclipseResourceFileSystemAccess.
The generated files will be formatted according to the Spray formatter config.
- stakeholder: Spray user
- keywords: Type: Enhancement, Priority: Medium
- status: DONE

## issue0018
Task: Generate org.xspray.mm classes in the build process
09.09.2011 13:10:31 (karsten.thoms): The metamodel classes in org.xspray.mm can be generated any time from the genmodel, and this can be automated in the build.
<b>TODO:</b>
- check metamodel classes for manual code. There is a derived attribute &quot;path&quot; for migration purposes of the templates that was introduced in issue#6
- Put the code into extension classes
- add MWE workflow to the project
- execute workflow in the build
- remove classes from src
11.09.2011 13:17:34 (karsten.thoms):
11.09.2011 13:31:10 (karsten.thoms): EMF Classes will be generated to `org.xspray.mm/emf-gen`.
A workflow `GenerateXsprayMM.mwe2` has been added to the project. This workflow is executed during the Maven build.
Manual implemented methods in the impl. classes (MetaAttribute#getPath()) have been replaced by extension methods in XsprayExtensions. Some minor modifications to the template were required.
Solved from build#30 on
https://spray.ci.cloudbees.com/job/spray-ci-build
- stakeholder: Spray user
- keywords: Type: Task
- status: DONE

## issue0019
Installation instructions
09.09.2011 16:58:03 (refsdal.ivar): <b>What steps will reproduce the problem?</b>
1. Download Eclipse Indigo MDT.
2. Add http://spray.eclipselabs.org.codespot.com/git.distribution/releases as an update site.
3. Select all.
4. Press next and then finish.
What is the expected output?
A successful install.
What do you see instead?
Cannot complete the install because one or more required items could not be found.
Software being installed: Spray SDK Feature 0.1.0 (org.xspray.feature.sdk.feature.group 0.1.0)
Missing requirement: org.xspray.xtext.tests 0.1.0 (org.xspray.xtext.tests 0.1.0) requires 'bundle org.eclipselabs.xtext.utils.unittesting 0.9.0' but it could not be found
Cannot satisfy dependency:
From: Spray SDK Feature 0.1.0 (org.xspray.feature.sdk.feature.group 0.1.0)
To: org.xspray.xtext.tests [0.1.0]
<b>What version of the product are you using? On what operating system?</b>
Was using a freshly unpacked eclipse-modeling-indigo-linux-gtk-x86_64.tar.gz
<b>Please provide any additional information below.</b>
Installation works fine with https://spray.ci.cloudbees.com/job/spray-ci-build/lastSuccessfulBuild/artifact/releng/repository/target/repository/
Examples would also be appreciated.
11.09.2011 13:17:03 (karsten.thoms):
11.09.2011 13:44:10 (karsten.thoms): The reason why this does not work with the release update site, but with the CI one is that the CI repository is now self-contained, which was done after releasing 0.1.0.
This issue will be fixed with releasing 0.2.0. Until then, I have changed the Install wiki page to mention to install from the CI site. I will change this when releasing the next time.
15.09.2011 16:38:55 (karsten.thoms): Released 0.2.0, update site will work now as expected.
- stakeholder: Spray user
- keywords: Type: Defect, Priority: Medium
- status: DONE

## issue0020
Missing package in example from CI build
09.09.2011 17:18:11 (refsdal.ivar): <b>What steps will reproduce the problem?</b>
1. Install everything from https://spray.ci.cloudbees.com/job/spray-ci-build/lastSuccessfulBuild/artifact/releng/repository/target/repository/(Date done: Fri Sep 9 17:16:08 CEST 2011)
into a fresh Eclipse Indigo MDT tool
2. &quot;Import&quot; -&gt; &quot;Plug-ins and Fragments&quot; -&gt;
Import from &quot;The active target platform&quot;
Plug-ins and Fragments to Import &quot;Select from all..&quot;
Import As &quot;Projects with source folders&quot;
3. Choose &quot;org.xspray.examples.one&quot;
<b>What is the expected output? What do you see instead?</b>
Build errors:
Description Resource Path Location Type
Package 'org.xspray.examples.mod4j.diagram' does not exist in this plug-in MANIFEST.MF /org.xspray.examples.one/META-INF line 6 Plug-in Problem
Package 'org.xspray.examples.mod4j.features' does not exist in this plug-in MANIFEST.MF /org.xspray.examples.one/META-INF line 6 Plug-in Problem
and associated errors due to this in mod4j-busmod.xspray.
Also there is no syntax highlighting or anything like that in
/org.xspray.examples.one/src/org/xspray/examples/one/XsprayGenerator.mwe2
Adding a dependency to the appropriate tooling would be nice.
<b>What version of the product are you using? On what operating system?</b>
Just eclipse-modeling-indigo-linux-gtk-x86_64.tar.gz
<b>Please provide any additional information below.</b>
Installing the Xtext SDK from http://download.eclipse.org/modeling/tmf/xtext/updates/composite/releases/ fixed the syntax highlighting/editor support for the .mwe2 file.
11.09.2011 13:53:22 (karsten.thoms): Confirmed, but I cannot really explain why the classes from /src-gen are not included. When exporting the project from Eclipse, the resulting Jars are fine. In the Maven build they are broken. Strange is that the same does work for other plugins, i.e. org.xspray.mm. Also there are classes in a second source folder, but they build correctly.
I will observe this problem and try a bit.
12.09.2011 14:01:31 (karsten.thoms): The missing MWE2 UI feature was solved with issue#26.
26.09.2011 12:39:28 (karsten.thoms): Added MWE2 workflow execution to the build of the example project.
The resulting Jars contain now the missing classes / sources.
Checked the Jars from Build#70, will be fixed with release 0.3.0.
- stakeholder: Spray user
- keywords: Type: Defect, Priority: Medium
- status: DONE

## issue0021
Provide Xspray new project wizard
11.09.2011 13:06:45 (karsten.thoms): Creation of Spray projects should be as easy as possible. A project wizard should be added to create a project with the structure as in org.xspray.example.one.
12.09.2011 10:04:23 (karsten.thoms):
12.09.2011 10:44:15 (karsten.thoms): Project wizard is implemented initially and pushed to master.
Todo:
The main package should now enable selecting an Ecore package. The plugin containing the Ecore package must be added to the reuired plugins. The genmodel for this package should be located to derive the "extension" value in the xspray model.
21.10.2011 22:12:10 (karsten.thoms): Considering this one as fixed now. The project wizard allows now selection of the Ecore model and Genmodel. The Ecore model can be selected from registered packages.
Added a second sheet to specify the generator settings.
- stakeholder: Spray user
- keywords: Type: Enhancement, Priority: Medium
- status: DONE

## issue0022
The generation gap classes are placed in src-gen, should be placed in src
11.09.2011 13:42:02 (de.abg.reichert.joerg): example: mod4jDiagramTypeProvider as well as mod4jDiagramTypeProviderBase are placed inside src-gen, but mod4jDiagramTypeProvider should reside in src, so changes would not get thrown away after regeneration
The Xspray generator should therefore define different outlets.
12.09.2011 17:21:03 (joswarmer): Generation of the 'empty' files (like mod4jDiagramTypeProvider ) in the src-gen folder is done on purpose. These need to be be generated in the src-gen folder. Only when a user wants to change a file, he should move it to the src folder. Advantages of this scheme are:
- regeneration as much as possible. Sometimes the 'empty' files change because of changes in the generator, , or sometimes they might need to contain some code.
- better overview for the user., He will only see files in the src folder that he has actually changed. Given the huge amount of files that may be generated it is not workable to generate them all in the src folder. It will be impossible for the user to find his manual changes.
12.09.2011 17:22:18 (joswarmer): I'll handle this one.
12.09.2011 17:26:56 (de.abg.reichert.joerg): Maybe we should consider the pattern used in Sculptor: http://fornax.itemis.de/confluence/display/fornax/3.+Advanced+Tutorial+(CSC)#3.AdvancedTutorial(CSC)-GapClass
i.e. introduce a keyword gap - only for elements in the DSL containing "gap" a gap class is generated: so if the user want to adapt a default behaviour he just annotate the element in the DSL with "gap"
12.09.2011 17:55:02 (joswarmer): We could go the Fornax way, but I see no big advantage. I have good experiences with the way it is done now. I propose to leave it as is, I think there are more pressing issues to deal with.
24.09.2011 22:15:36 (Alex.Roldugin): So, if I want to change mod4jDiagramTypeProvider.java file, I have to move it from src-gen to src directory and then make changes? But if it's so, after code-regeneration mod4jDiagramTypeProvider.java appears in src-gen again and I'll get 'The type mod4jDiagramTypeProvider is already defined'. So, now it's bug - am I right?
25.09.2011 21:59:00 (joswarmer): No, it works slightly more intelligent. If the file is moved to src the generator will recognize that it has been moved and will not generate the file again.
28.09.2011 20:37:53 (Alex.Roldugin): Yes, you're right! I found this place in org.eclipselabs.spray.generator.graphiti.templates.SprayGenerator.xtend
But. I cannot understand why, but if I create new spray(0.2.0)-project (using wizard, with default settings) - source code generates perfectly in "src-gen"!
Then I create org.eclipselabs.spray.examples.mydiagram.diagram package in "src" and copy here some file (e.g. MyDiagramDiagramTypeProvider) from "src-gen" (from the same package) to "src" and try to clean and rebuild workspace, then I got two MyDiagramDiagramTypeProvider.java files (in "src" and "src-gen") and "The type MyDiagramDiagramTypeProvider is already defined"-error for those that lays in "src".
Jos, maybe You know (or someone else) quick way to fix this error or maybe I do something wrong?
28.09.2011 20:44:22 (Alex.Roldugin): *In FileGenerator.xtend, not in SprayGenerator.xtend
28.09.2011 23:45:42 (Alex.Roldugin): If I ran eclipse with enabled -consoleLog then I got this log:
PROPERTIES [platform:/resource/org.eclipselabs.spray.examples.MyDiagram/model/MyDiagram.properties]
EclipseResourceFileSystemAccess: WARNING: dos not work yet
generating org/eclipselabs/spray/examples/mydiagram/diagram/MyDiagramDiagramTypeProvider.java
....
PS: I use Windows XP
03.10.2011 16:13:28 (jos.warmer@openmodeling.nl): Make sure that the file you are copying is meant to be used for manual extensions /overriding. The base class never is and will always be generated. You can see this in the generated comment at the start of the file. Can you check this?
03.10.2011 16:51:05 (Alex.Roldugin): Yes. I saw all this comments about extension point, so it was my first step for working with spray - copy this file (without suffix Base) to "src".
I went through project's source codes and found that in my case for some reason for source code generation used not JavaIoFileSystemAccess', but EclipseResourceFileSystemAccess' object. So that's why we see warning: *EclipseResourceFileSystemAccess: WARNING: dos not work yet*
(you can see it in SprayGraphityGenerator.xtend::doGenerate)
And I think because of this generator looks for file not in workspace directory, but in eclipse start directory (e.g. C:\Program Files\eclipse\).
So in my case for generation uses JavaGenFile's object with uninitialized Gen and Man output pathes (the same doGenerate method), at least we should add:
if( javaFsa != null ){
java = new JavaGenFile(javaFsa)
java.setGenOutputPath(genOutputPath)
java.setManOutputPath(manOutputPath)
} else {
java = new JavaGenFile(eclipseFsa)
// add two following lines
java.setGenOutputPath(genOutputPath)
java.setManOutputPath(manOutputPath)
}
After adding this lines generator again will looks for file in eclipse's start directory. But if we set eclipse start directory to workspace directory it works pretty well. Ofcourse it isn't right solution, but as quick fix can be used.
Maybe you know what should I do to make generator use JavaIoFileSystemAccess' object instead of EclipseResourceFileSystemAccess'?
05.10.2011 09:31:51 (jos.warmer@openmodeling.nl): Right, when I committed the first code, this was only working while running the generator from the Main program, not inside Eclipse. I'll take a look how to fix this for buildinh inside Eclipse
08.10.2011 21:51:13 (Alex.Roldugin): Can you, at least, add those two lines of initializing gen and man pathes as I mention above to repository - it helps me to omit adding this modifications by myself and rebuilding spray any time I sync with your's repository.
Can you do this for me?
18.10.2011 10:43:00 (de.abg.reichert.joerg): with commit 8a4ab0272644c2655cda8678df90141126706e50 the output paths are added as requested in #c14
18.10.2011 10:45:40 (de.abg.reichert.joerg): As discussed yesterday it is very likely that in the future there will be a configuration file in the project that registers all classes for that a gap class should be generated. To ease that configuration there will be UI enhancements that support creating new gap classes from existing generated classes.
18.10.2011 15:04:03 (joswarmer): I'll handle this one. The path should only be used when not inside Eclipse. Within Eclipse we should use the project to find the location for the different folders.
18.10.2011 17:19:49 (joswarmer): Changed code generation in Eclipse to use the project location instead of the projectPath from the properties file. Now the generator works standalone and as an eclipse builder.
Also repaired the fact that extension point files that were moved to 'src' were still generated.
- stakeholder: Spray user
- keywords: Type: Defect, Priority: Medium, generator
- status: DONE

## issue0023
DSL and generator does not support defining figures containing images
11.09.2011 13:47:13 (de.abg.reichert.joerg): It should be possible to define a figure that contains an image. In the implementation the image would be a child of the figure, e.g. a rectangle. The image itself has optional a width and height as well as a position inside the shape.
13.09.2011 09:20:24 (de.abg.reichert.joerg): I'll handle this one.
13.09.2011 23:09:18 (joswarmer):
13.04.2012 11:19:17 (de.abg.reichert.joerg): Duplicate of issue #121
- stakeholder: Spray user
- keywords: Type: Enhancement, Priority: Medium
- status: DONE

## issue0024
Provide Spray diagram wizard
11.09.2011 13:52:58 (de.abg.reichert.joerg): Beside the project wizard in issue http://code.google.com/a/eclipselabs.org/p/spray/issues/detail?id=21 there should be also a diagram wizard that allows to choose, if the domain model should be contained in the diagram file or should be separated stored in an extra file. Furthermore the wizard should enable to choose an existing domain model file to create a diagram file fore.
Further improvements would be to support choosing different diagram types operating as different views on the same domain model, but maybe this should be tracked in an extra issue report.
05.11.2011 18:30:28 (joswarmer):
09.11.2011 11:40:10 (de.abg.reichert.joerg):
13.04.2012 08:13:25 (karsten.thoms): This issue was closed by revision 7d517f9d647b.
- stakeholder: Spray user
- keywords: Type: Enhancement, Priority: Low
- status: DONE

## issue0025
Could not build Xspray locally
11.09.2011 15:51:31 (de.abg.reichert.joerg): I run into that problem under MacOS as well as under Windows XP. I use Maven 3.0.3. With mvn clean install in the releng folder I finally end up with the output below (what is strange as the build in Cloudbees' Jenkins obvious works):
-------------------------------------------------------
T E S T S
-------------------------------------------------------
Running org.xspray.xtext.tests.Mod4jTest
11.09.2011 15:44:49 org.eclipse.emf.mwe.utils.StandaloneSetup setPlatformUri
INFO: Registering platform uri 'C:\git\spray\tests'
log4j:WARN No appenders could be found for logger (org.eclipselabs.xtext.utils.u
nittesting.XtextTest).
log4j:WARN Please initialize the log4j system properly.
Tests run: 1, Failures: 0, Errors: 1, Skipped: 0, Time elapsed: 1.282 sec &lt;&lt;&lt; FA
ILURE!
test_mod4j_busmod(org.xspray.xtext.tests.Mod4jTest) Time elapsed: 1 sec &lt;&lt;&lt; ER
ROR!
org.eclipse.xtext.resource.ClasspathUriResolutionException: java.lang.IllegalSta
teException: Couldn't find resource on classpath. URI was 'classpath:///mod4j/Bu
sinessDomainDsl.ecore'
at org.eclipse.xtext.resource.ClassloaderClasspathUriResolver.resolve(Cl
assloaderClasspathUriResolver.java:48)
at org.eclipse.xtext.resource.XtextResourceSet.resolveClasspathURI(Xtext
ResourceSet.java:35)
at org.eclipse.xtext.resource.XtextResourceSet.access$0(XtextResourceSet
.java:34)
at org.eclipse.xtext.resource.XtextResourceSet$1.normalize(XtextResource
Set.java:53)
at org.eclipse.emf.ecore.resource.impl.ExtensibleURIConverterImpl.create
InputStream(ExtensibleURIConverterImpl.java:349)
at org.eclipse.emf.ecore.resource.impl.ResourceImpl.load(ResourceImpl.ja
va:1262)
at org.eclipselabs.xtext.utils.unittesting.XtextTest.loadModel(XtextTest
.java:406)
at org.eclipselabs.xtext.utils.unittesting.XtextTest.testFile(XtextTest.
java:175)
at org.xspray.xtext.tests.Mod4jTest.test_mod4j_busmod(Mod4jTest.java:26)
at sun.reflect.NativeMethodAccessorImpl.invoke0(Native Method)
at sun.reflect.NativeMethodAccessorImpl.invoke(NativeMethodAccessorImpl.
java:39)
at sun.reflect.DelegatingMethodAccessorImpl.invoke(DelegatingMethodAcces
sorImpl.java:25)
at java.lang.reflect.Method.invoke(Method.java:597)
at org.junit.runners.model.FrameworkMethod$1.runReflectiveCall(Framework
Method.java:44)
at org.junit.internal.runners.model.ReflectiveCallable.run(ReflectiveCal
lable.java:15)
at org.junit.runners.model.FrameworkMethod.invokeExplosively(FrameworkMe
thod.java:41)
at org.junit.internal.runners.statements.InvokeMethod.evaluate(InvokeMet
hod.java:20)
at org.junit.internal.runners.statements.RunBefores.evaluate(RunBefores.
java:28)
at org.junit.internal.runners.statements.RunAfters.evaluate(RunAfters.ja
va:31)
at org.eclipse.xtext.junit4.XtextRunner$1.evaluate(XtextRunner.java:55)
at org.junit.runners.BlockJUnit4ClassRunner.runNotIgnored(BlockJUnit4Cla
ssRunner.java:79)
at org.junit.runners.BlockJUnit4ClassRunner.runChild(BlockJUnit4ClassRun
ner.java:71)
at org.junit.runners.BlockJUnit4ClassRunner.runChild(BlockJUnit4ClassRun
ner.java:49)
at org.junit.runners.ParentRunner$3.run(ParentRunner.java:193)
at org.junit.runners.ParentRunner$1.schedule(ParentRunner.java:52)
at org.junit.runners.ParentRunner.runChildren(ParentRunner.java:191)
at org.junit.runners.ParentRunner.access$000(ParentRunner.java:42)
at org.junit.runners.ParentRunner$2.evaluate(ParentRunner.java:184)
at org.junit.internal.runners.statements.RunBefores.evaluate(RunBefores.
java:28)
at org.junit.runners.ParentRunner.run(ParentRunner.java:236)
at org.apache.maven.surefire.junit4.JUnit4TestSet.execute(JUnit4TestSet.
java:62)
at org.apache.maven.surefire.suite.AbstractDirectoryTestSuite.executeTes
tSet(AbstractDirectoryTestSuite.java:140)
at org.apache.maven.surefire.suite.AbstractDirectoryTestSuite.execute(Ab
stractDirectoryTestSuite.java:127)
at org.apache.maven.surefire.Surefire.run(Surefire.java:177)
at org.eclipse.tycho.surefire.osgibooter.OsgiSurefireBooter.run(OsgiSure
fireBooter.java:72)
at org.eclipse.tycho.surefire.osgibooter.HeadlessTestApplication.run(Hea
dlessTestApplication.java:21)
at sun.reflect.NativeMethodAccessorImpl.invoke0(Native Method)
at sun.reflect.NativeMethodAccessorImpl.invoke(NativeMethodAccessorImpl.
java:39)
at sun.reflect.DelegatingMethodAccessorImpl.invoke(DelegatingMethodAcces
sorImpl.java:25)
at java.lang.reflect.Method.invoke(Method.java:597)
at org.eclipse.equinox.internal.app.EclipseAppContainer.callMethodWithEx
ception(EclipseAppContainer.java:587)
at org.eclipse.equinox.internal.app.EclipseAppHandle.run(EclipseAppHandl
e.java:198)
at org.eclipse.core.runtime.internal.adaptor.EclipseAppLauncher.runAppli
cation(EclipseAppLauncher.java:110)
at org.eclipse.core.runtime.internal.adaptor.EclipseAppLauncher.start(Ec
lipseAppLauncher.java:79)
at org.eclipse.core.runtime.adaptor.EclipseStarter.run(EclipseStarter.ja
va:344)
at org.eclipse.core.runtime.adaptor.EclipseStarter.run(EclipseStarter.ja
va:179)
at sun.reflect.NativeMethodAccessorImpl.invoke0(Native Method)
at sun.reflect.NativeMethodAccessorImpl.invoke(NativeMethodAccessorImpl.
java:39)
at sun.reflect.DelegatingMethodAccessorImpl.invoke(DelegatingMethodAcces
sorImpl.java:25)
at java.lang.reflect.Method.invoke(Method.java:597)
at org.eclipse.equinox.launcher.Main.invokeFramework(Main.java:622)
at org.eclipse.equinox.launcher.Main.basicRun(Main.java:577)
at org.eclipse.equinox.launcher.Main.run(Main.java:1410)
at org.eclipse.equinox.launcher.Main.main(Main.java:1386)
Caused by: java.lang.IllegalStateException: Couldn't find resource on classpath.
URI was 'classpath:///mod4j/BusinessDomainDsl.ecore'
at org.eclipse.xtext.resource.ClassloaderClasspathUriResolver.findResour
ceOnClasspath(ClassloaderClasspathUriResolver.java:60)
at org.eclipse.xtext.resource.ClassloaderClasspathUriResolver.resolve(Cl
assloaderClasspathUriResolver.java:45)
... 53 more
Results :
Tests in error:
test_mod4j_busmod(org.xspray.xtext.tests.Mod4jTest)
Tests run: 1, Failures: 0, Errors: 1, Skipped: 0
[INFO] ------------------------------------------------------------------------
[INFO] Reactor Summary:
[INFO]
[INFO] Eclipselabs Spray ................................. SUCCESS [0.422s]
[INFO] org.xspray.mm ..................................... SUCCESS [42.281s]
[INFO] org.xspray.generator.graphiti ..................... SUCCESS [1.515s]
[INFO] org.xspray.runtime ................................ SUCCESS [0.922s]
[INFO] org.xspray.xtext .................................. SUCCESS [15.485s]
[INFO] org.xspray.xtext.ui ............................... SUCCESS [3.593s]
[INFO] org.mod4j.dsl.businessdomain.mm ................... SUCCESS [1.032s]
[INFO] org.xspray.examples.one ........................... SUCCESS [1.343s]
[INFO] org.xspray.xtext.tests ............................ FAILURE [1:11.547s]
[INFO] org.xspray.examples.one.tests ..................... SKIPPED
[INFO] org.xspray.feature ................................ SKIPPED
[INFO] org.xspray.feature.source ......................... SKIPPED
[INFO] org.xspray.feature.sdk ............................ SKIPPED
[INFO] org.xspray.releng.repository ...................... SKIPPED
[INFO] ------------------------------------------------------------------------
11.09.2011 16:24:36 (de.abg.reichert.joerg): having m2eclipse installed and using /org.xspray.releng/launch/spray clean package.launch, the build works.
11.09.2011 16:37:43 (de.abg.reichert.joerg): mvn clean package does not execute the tests, mvn clean install does. When the test executed then the example is accessed via the classpath protocol.
12.09.2011 11:49:49 (karsten.thoms):
13.09.2011 15:17:53 (karsten.thoms): Maven build works now.
The DSL tests are executed with "classic" surefire plugin, tycho-surefire-plugin has been disabled.
SWT Bot tests are included in the build, but deactivated for the CI build.
- stakeholder: Spray user
- keywords: Type: Defect, Priority: Medium, build
- status: DONE

## issue0026
MWE2 UI not installed in Spray SDK
12.09.2011 13:22:26 (karsten.thoms): The org.xspray.examples.one project contains an MWE2 workflow. When installing the Spray SDK feature the MWE2 editor is not available.
The target platform must be extended by MWE2 and also the Spray SDK feature.
12.09.2011 14:00:45 (karsten.thoms): Fixed with 0.2.0, Build#36
https://spray.ci.cloudbees.com/job/spray-ci-build/
- stakeholder: Spray user
- keywords: Type: Defect, Priority: Medium
- status: DONE

## issue0027
Rename projects to prefix "org.eclipselabs.spray"
14.09.2011 05:49:52 (karsten.thoms): The projects have been developed with prefix &quot;org.xspray&quot;, since we have a nameclash with another project named &quot;Spray&quot; (https://github.com/spray/spray/wiki). We agreed with the other Spray project that we can also leave the name &quot;Spray&quot;. Further, Eclipselabs encourages to choose the prefix &quot;org.eclipselabs&quot; (http://www.eclipse.org/org/foundation/eclipselabs/guidelines.php).
Thus the projects should be renamed to `org.eclipselabs.spray.xxxxx`, same for base packages.
14.09.2011 11:11:45 (karsten.thoms): - renamed project names org.xspray -> org.eclipselabs.xspray
- renamed project org.xspray.runtime -> org.eclipselabs.spray.runtime.graphiti
- renamed directory names according to plugin names
- moved
org.eclipselabs.spray.examples.one
org.mod4j.businessdomain.mm
to subdirectory examples/one
- changed relative paths in the pom.xml files
- renamed xspray.ecore/.genmodel -> spray.ecore/.genmodel
- adjusted paths in genmodel and ecore file
- changed package name in spray.ecore to 'spray'
- renamed Xspray.xtext -> Spray.xtext
- renamed project artifacts with "Xspray" prefix to "Spray" prefix
- searched all files for occurances of "xspray" by "spray"
Note that the file extension changes also to .spray!
14.09.2011 11:57:33 (karsten.thoms): Pushed to repository and build is working (build#49).
- stakeholder: Spray user
- keywords: Type: Task
- status: DONE

## issue0028
Add feature/plugin properties
15.09.2011 11:46:27 (karsten.thoms): All relevant information like plugin/feature name, provider, license etc. should be externalized into
- plugin.properties
- feature.properties
For features, add license file, about file, logo and include them to bin.includes in the build.properties.
For plugins, set
Bundle-Localization: plugin
in the MANIFEST.MF
15.09.2011 14:44:05 (karsten.thoms): Fixed with 0.2.0
- stakeholder: Spray user
- keywords: Type: Task
- status: DONE

## issue0029
Add content assist for Icons
16.09.2011 11:04:49 (karsten.thoms): The string entered for &quot;icon&quot; is free hand. It is not checked that the icon does exist, nor you can see it in action without starting the runtime.
If activating the content assist in the icon STRING it should propose the paths of known icons: at least those residing in the project, then maybe also from dependent plugins. If possible, show the icon also in the hover information.
22.09.2011 01:09:45 (karsten.thoms): - Added UI specific validator SprayJavaUIValidator and bound to UI Module
- Implemented validation checks for MetaClass#icon:
- ERROR when folder /icons does not exist in Spray project
- WARNING when the configured icon file is not found below /icons
- WARNING when the file has an unknown file extension (list of valid valies configured in SprayRuntimeModule)
- Added content assist for Icon path including displaying the Image, see attached screenshot
- stakeholder: Spray user
- keywords: Type: Enhancement, Priority: Medium
- status: DONE

## issue0030
Generated class names
22.09.2011 21:33:25 (karsten.thoms): The class names should have different casing, see Example One
1) class names begin with small letter 'mod4j', but class names should start with capital letter
mod4jAddAssociationFeatureBase
=&gt; Mod4jAddAssociationFeatureBase
2) Names of references must start with capital letter
mod4jCreateBusinessClassbusinessRulesBusinessRuleFeature
=&gt; Mod4jCreateBusinessClassBusinessRulesBusinessRuleFeature
25.09.2011 23:18:07 (karsten.thoms): Changed naming pattern. All class names are computed by class NamingExtensions.
- stakeholder: Spray user
- keywords: Type: Defect, Priority: Medium
- status: DONE

## issue0031
Use ImportUtil to manage imports in templates
23.09.2011 08:29:09 (karsten.thoms): Templates contain sometimes a huge amount of logic to create the right imports. For example, FeatureProvider.xtend uses 50 lines of code just for computed imports.
{{{
...
import «feature_package()».«diagram.name»Layout«cls.visibleName()»Feature; // 4
«IF cls.representedBy instanceof Container»
«var container = cls.representedBy as Container »
«FOR MetaReference reference : container.parts.filter(typeof(MetaReference)) »
«var references = cls.type.EAllReferences »
«val referenceName = reference.getName»
«var target = references.findFirst(e|e.name == referenceName ) »
«IF ! target.EReferenceType.abstract»
import «feature_package()».«cls.diagram.name»Create«cls.getName»«reference.getName»«target.EReferenceType.name»Feature;
...
}}}
Therefore there is the ImportUtil class, which uses an ImportManager to collect the qualified names of used classes, and prints out the simple name.
To use it, the body of a template must be evaluated first before printing out the imports. As a reference look at AddConnectionFeature.xtend, the mainFile() method initializes ImportUtil and delegates to mainFileBody to evaluate the file content and their imports.
23.09.2011 13:58:19 (joswarmer): The class XtendProperties in Spray also contains an import manager that is used already in some of the Spray templates. I just did no get around to use it in all templates. Can we compare the use of ImportUtil and XtendProperties ?
26.09.2011 12:33:03 (karsten.thoms):
27.09.2011 11:27:19 (karsten.thoms): I will investigate the use of XtendProperties. The import manager used there is quite simple. I have leveraged the one from EMF, which is far more advanced. I am not completely sure in which extend it does also more for us. But I'd prefer to reuse such a component before having an own one.
27.09.2011 11:35:03 (joswarmer): Sounds like a good idea, if the already existing one ash everything we need, let's reuse it.
27.09.2011 12:01:12 (karsten.thoms): I have documented the pattern here:
http://code.google.com/a/eclipselabs.org/p/spray/wiki/DevGuide_Generator?ts=1317117450&updated=DevGuide_Generator#Import_Organizing
If possible I want to get rid of calling 'importUtil.initImports', or just move it to FileGenerator.
04.10.2011 07:20:16 (karsten.thoms): Moved logic to FileGenerator and refactored template code. Using the "MARKER_IMPORT" marker comment.
Updated DevGuide: http://code.google.com/a/eclipselabs.org/p/spray/wiki/DevGuide_Generator
- stakeholder: Spray user
- keywords: Type: Defect, Priority: Medium
- status: DONE

## issue0032
Cannot open generated diagram editor
25.09.2011 18:20:17 (de.abg.reichert.joerg): The editor fails with an exception, that the EClass cannot be resolved.
Date: Sun, 25 Sep 2011 13:44:07 +0200
From: Soeren Dierkes &lt;soeren.dierkes@informatik.uni-oldenburg.de&gt;
To: graphiti-dev@eclipse.org
Subject: [graphiti-dev] First Editor
Message-ID: &lt;4E7F1407.5090800@informatik.uni-oldenburg.de&gt;
Content-Type: text/plain; charset=ISO-8859-15; format=flowed
Hey everyone,
I know its not the common way to ask via dev-mailinglist, but no one
answered me in my thread, so I decide to ask you.
I think the answer should be pretty easy, but I dont get it for my own.
Its my first try to develop a plugin, and I start with your tutorial
and just copy paste the first classes to test it and
reconfigure it to understand the API.
I am able to create a new editor, but if I try to open it there is no
EClass object and I got the exception:
Contributor mytutorial.PropertyContributor cannot be created.
Later in your tutorial it is described how I add this to the plugin.xml
and I think I did it like I should.
But now I got nothing, no exception, no EClass, no warning.
Ive tried everything I know, but it doesnt work.
Last step, ask some developer.
I hope you can help me
Soeren
25.09.2011 19:23:10 (de.abg.reichert.joerg): this exception occurs when you try to open the mod4j_busmod.spray file:
java.lang.IllegalStateException: Cannot determine interface name for EClass, since the EClass is an unresolved proxy (platform:/resource/org.eclipse.xtext.example.fowlerdsl.diagram/model/fowler.spray#xtextLink_::0.2.0::8::/2)
at org.eclipselabs.spray.xtext.jvmmodel.GenModelHelper.getJavaInterfaceName(GenModelHelper.java:29)
at org.eclipselabs.spray.xtext.jvmmodel.SprayJvmModelInferrer._transform(SprayJvmModelInferrer.java:89)
at org.eclipselabs.spray.xtext.jvmmodel.SprayJvmModelInferrer.transform(SprayJvmModelInferrer.java:121)
at org.eclipselabs.spray.xtext.jvmmodel.SprayJvmModelInferrer$1.apply(SprayJvmModelInferrer.java:67)
at org.eclipselabs.spray.xtext.jvmmodel.SprayJvmModelInferrer$1.apply(SprayJvmModelInferrer.java:1)
at org.eclipse.xtext.xbase.lib.IterableExtensions$FunctionDelegate.apply(IterableExtensions.java:724)
at com.google.common.collect.Lists$TransformingRandomAccessList.get(Lists.java:431)
at java.util.AbstractList$Itr.next(AbstractList.java:345)
at com.google.common.collect.Iterators$8.next(Iterators.java:696)
at com.google.common.collect.Iterators$5.hasNext(Iterators.java:505)
at com.google.common.collect.Lists.newArrayList(Lists.java:131)
at com.google.common.collect.Lists.newArrayList(Lists.java:113)
at org.eclipse.xtext.xbase.lib.IterableExtensions.toList(IterableExtensions.java:571)
at org.eclipselabs.spray.xtext.jvmmodel.SprayJvmModelInferrer.inferJvmModel(SprayJvmModelInferrer.java:52)
at org.eclipse.xtext.xbase.jvmmodel.JvmModelXbaseLazyLinker.afterModelLinked(JvmModelXbaseLazyLinker.java:57)
at org.eclipse.xtext.linking.impl.AbstractCleaningLinker.linkModel(AbstractCleaningLinker.java:44)
at org.eclipse.xtext.resource.XtextResource.doLinking(XtextResource.java:249)
at org.eclipse.xtext.linking.lazy.LazyLinkingResource.doLinking(LazyLinkingResource.java:77)
at org.eclipse.xtext.resource.XtextResource.updateInternalState(XtextResource.java:217)
at org.eclipse.xtext.resource.XtextResource.doLoad(XtextResource.java:152)
at org.eclipse.xtext.linking.lazy.LazyLinkingResource.doLoad(LazyLinkingResource.java:70)
at org.eclipse.emf.ecore.resource.impl.ResourceImpl.load(ResourceImpl.java:1511)
at org.eclipse.xtext.ui.editor.model.XtextDocumentProvider.loadResource(XtextDocumentProvider.java:138)
at org.eclipse.xtext.ui.editor.model.XtextDocumentProvider.setDocumentContent(XtextDocumentProvider.java:119)
at org.eclipse.ui.editors.text.StorageDocumentProvider.createDocument(StorageDocumentProvider.java:229)
at org.eclipse.xtext.ui.editor.model.XtextDocumentProvider.createDocument(XtextDocumentProvider.java:88)
at org.eclipse.ui.editors.text.FileDocumentProvider.createElementInfo(FileDocumentProvider.java:735)
at org.eclipse.xtext.ui.editor.model.XtextDocumentProvider.createElementInfo(XtextDocumentProvider.java:149)
at org.eclipse.ui.texteditor.AbstractDocumentProvider.connect(AbstractDocumentProvider.java:400)
at org.eclipse.ui.texteditor.AbstractTextEditor.doSetInput(AbstractTextEditor.java:4213)
at org.eclipse.ui.texteditor.StatusTextEditor.doSetInput(StatusTextEditor.java:237)
at org.eclipse.ui.texteditor.AbstractDecoratedTextEditor.doSetInput(AbstractDecoratedTextEditor.java:1451)
at org.eclipse.ui.editors.text.TextEditor.doSetInput(TextEditor.java:169)
at org.eclipse.ui.texteditor.AbstractTextEditor$19.run(AbstractTextEditor.java:3200)
at org.eclipse.jface.operation.ModalContext.runInCurrentThread(ModalContext.java:464)
at org.eclipse.jface.operation.ModalContext.run(ModalContext.java:372)
at org.eclipse.jface.window.ApplicationWindow$1.run(ApplicationWindow.java:759)
at org.eclipse.swt.custom.BusyIndicator.showWhile(BusyIndicator.java:70)
at org.eclipse.jface.window.ApplicationWindow.run(ApplicationWindow.java:756)
at org.eclipse.ui.internal.WorkbenchWindow.run(WorkbenchWindow.java:2642)
at org.eclipse.ui.texteditor.AbstractTextEditor.internalInit(AbstractTextEditor.java:3218)
at org.eclipse.ui.texteditor.AbstractTextEditor.init(AbstractTextEditor.java:3245)
at org.eclipse.ui.internal.EditorManager.createSite(EditorManager.java:828)
at org.eclipse.ui.internal.EditorReference.createPartHelper(EditorReference.java:647)
at org.eclipse.ui.internal.EditorReference.createPart(EditorReference.java:465)
at org.eclipse.ui.internal.WorkbenchPartReference.getPart(WorkbenchPartReference.java:595)
at org.eclipse.ui.internal.EditorReference.getEditor(EditorReference.java:289)
at org.eclipse.ui.internal.WorkbenchPage.busyOpenEditorBatched(WorkbenchPage.java:2945)
at org.eclipse.ui.internal.WorkbenchPage.busyOpenEditor(WorkbenchPage.java:2850)
at org.eclipse.ui.internal.WorkbenchPage.access$11(WorkbenchPage.java:2842)
at org.eclipse.ui.internal.WorkbenchPage$10.run(WorkbenchPage.java:2793)
at org.eclipse.swt.custom.BusyIndicator.showWhile(BusyIndicator.java:70)
at org.eclipse.ui.internal.WorkbenchPage.openEditor(WorkbenchPage.java:2789)
at org.eclipse.ui.internal.WorkbenchPage.openEditor(WorkbenchPage.java:2773)
at org.eclipse.ui.internal.WorkbenchPage.openEditor(WorkbenchPage.java:2764)
at org.eclipse.ui.ide.IDE.openEditor(IDE.java:651)
at org.eclipse.ui.ide.IDE.openEditor(IDE.java:610)
at org.eclipse.jdt.internal.ui.javaeditor.EditorUtility.openInEditor(EditorUtility.java:355)
at org.eclipse.jdt.internal.ui.javaeditor.EditorUtility.openInEditor(EditorUtility.java:164)
at org.eclipse.jdt.ui.actions.OpenAction.run(OpenAction.java:249)
at org.eclipse.jdt.ui.actions.OpenAction.run(OpenAction.java:228)
at org.eclipse.jdt.ui.actions.SelectionDispatchAction.dispatchRun(SelectionDispatchAction.java:275)
at org.eclipse.jdt.ui.actions.SelectionDispatchAction.run(SelectionDispatchAction.java:251)
at org.eclipse.jdt.internal.ui.navigator.OpenAndExpand.run(OpenAndExpand.java:50)
at org.eclipse.ui.actions.RetargetAction.run(RetargetAction.java:221)
at org.eclipse.ui.navigator.CommonNavigatorManager$3.open(CommonNavigatorManager.java:185)
at org.eclipse.ui.OpenAndLinkWithEditorHelper$InternalListener.open(OpenAndLinkWithEditorHelper.java:48)
at org.eclipse.jface.viewers.StructuredViewer$2.run(StructuredViewer.java:866)
at org.eclipse.core.runtime.SafeRunner.run(SafeRunner.java:42)
at org.eclipse.ui.internal.JFaceUtil$1.run(JFaceUtil.java:49)
at org.eclipse.jface.util.SafeRunnable.run(SafeRunnable.java:175)
at org.eclipse.jface.viewers.StructuredViewer.fireOpen(StructuredViewer.java:864)
at org.eclipse.jface.viewers.StructuredViewer.handleOpen(StructuredViewer.java:1152)
at org.eclipse.ui.navigator.CommonViewer.handleOpen(CommonViewer.java:462)
at org.eclipse.jface.viewers.StructuredViewer$6.handleOpen(StructuredViewer.java:1256)
at org.eclipse.jface.util.OpenStrategy.fireOpenEvent(OpenStrategy.java:275)
at org.eclipse.jface.util.OpenStrategy.access$2(OpenStrategy.java:269)
at org.eclipse.jface.util.OpenStrategy$1.handleEvent(OpenStrategy.java:309)
at org.eclipse.swt.widgets.EventTable.sendEvent(EventTable.java:84)
at org.eclipse.swt.widgets.Display.sendEvent(Display.java:4125)
at org.eclipse.swt.widgets.Widget.sendEvent(Widget.java:1457)
at org.eclipse.swt.widgets.Widget.sendEvent(Widget.java:1480)
at org.eclipse.swt.widgets.Widget.sendEvent(Widget.java:1465)
at org.eclipse.swt.widgets.Widget.notifyListeners(Widget.java:1270)
at org.eclipse.swt.widgets.Display.runDeferredEvents(Display.java:3971)
at org.eclipse.swt.widgets.Display.readAndDispatch(Display.java:3610)
at org.eclipse.ui.internal.Workbench.runEventLoop(Workbench.java:2696)
at org.eclipse.ui.internal.Workbench.runUI(Workbench.java:2660)
at org.eclipse.ui.internal.Workbench.access$4(Workbench.java:2494)
at org.eclipse.ui.internal.Workbench$7.run(Workbench.java:674)
at org.eclipse.core.databinding.observable.Realm.runWithDefault(Realm.java:332)
at org.eclipse.ui.internal.Workbench.createAndRunWorkbench(Workbench.java:667)
at org.eclipse.ui.PlatformUI.createAndRunWorkbench(PlatformUI.java:149)
at org.eclipse.ui.internal.ide.application.IDEApplication.start(IDEApplication.java:123)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:344)
at org.eclipse.core.runtime.adaptor.EclipseStarter.run(EclipseStarter.java:179)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.eclipse.equinox.launcher.Main.invokeFramework(Main.java:622)
at org.eclipse.equinox.launcher.Main.basicRun(Main.java:577)
at org.eclipse.equinox.launcher.Main.run(Main.java:1410)
at org.eclipse.equinox.launcher.Main.main(Main.java:1386)
25.09.2011 23:17:26 (karsten.thoms): You will get this error only when the index was not built. This may happen when you start the workbench when the last time exited an Spray editor was opened before.
After the build is through, the Spray editor should be working.
Lowering severity.
09.11.2011 11:39:30 (de.abg.reichert.joerg): Did not encounter this problem anymore, so I close this bug.
- stakeholder: Spray user
- keywords: Type: Defect, Priority: High
- status: DONE

## issue0033
Move complete generator logic to o.e.s.generator.graphiti
26.09.2011 13:26:47 (karsten.thoms): The Spray language plugin should not have a dependency on Graphiti related plugins (o.e.s.generator.graphiti, o.e.s.runtime.graphiti), the dependency must be vice versa.
The reason why o.e.s.xtext depends on o.e.s.generator.graphiti is that SprayGenerator.xtend invokes the Graphiti generator. The classes from package o.e.s.xtext.generator must be moved to o.e.s.graphiti.generator.
To trigger the build in the UI as before, a BuilderParticipant must be registered outside of the language plugins. Since this is UI related, a new plugin o.e.s.generator.graphiti.ui must be introduced.
As a result, o.e.s.xtext must not have a dependency to any *.graphiti.* plugin and the code generator in the UI must still be triggered on model save.
28.09.2011 11:35:54 (karsten.thoms): Added new project org.eclipselabs.spray.generator.graphiti.ui
Described changes in detail in this blog post:
http://kthoms.wordpress.com/2011/09/28/moving-an-xtend-generator-into-its-own-plugin/
- stakeholder: Spray user
- keywords: Type: Defect, Priority: Medium
- status: DONE

## issue0034
Allow user defined RGB color values
27.09.2011 15:00:28 (karsten.thoms): Colors should not only be restricted to IColorConstant instances, it should also be allowed to define a color with RGB values.
line (width=2 color=RGB(128,128,128));
Sebastian Zarnekow has written an article to include a Color Picker dialog to choose the RGB color.
http://zarnekow.blogspot.com/2011/06/customizing-content-assist-with-xtext.html
30.09.2011 22:59:22 (karsten.thoms): Introduced metaclass "Color" and "RGBColor"
Changed grammar, added RGBColor
RGB(r,g,b)
Added unit test
Implemented content assist
- stakeholder: Spray user
- keywords: Type: Enhancement, Priority: Medium
- status: DONE

## issue0035
Remove dependencies to Graphiti plugins from DSL plugins
28.09.2011 12:45:08 (karsten.thoms): The o.e.s.xtext.ui plugin has dependencies to the Spray Graphiti plugins. This dependency must be removed.
It has to be investigated if the extension point org.eclipse.xtext.ui.shared.overridingGuiceModule can be used to achieve this.
12.11.2012 17:50:44 (joswarmer):
12.11.2012 18:03:53 (joswarmer):
- stakeholder: Spray user
- keywords: Type: Task, Priority: Low
- status: READY

## issue0036
Provide documentation plugin
30.09.2011 11:16:16 (karsten.thoms): We need to provide our documentation in a format that is consumable in the following formats:
- HTML
- Eclipse Help
- PDF
The documentation should be easily to write. The production of the different formats must be integrated into the build, maybe only if a specific profile is activated.
The documentation project has to be created at location /docs in the repository as an Eclipse project.
Specify the required plugins to install to the IDE to develop the documentation.
Possible candidates for documentation format:
- Mylyn WikiText
- eWiki - http://nirmalsasidharan.wordpress.com/category/mylyn/
- Xdoc - http://zarnekow.blogspot.com/2011/06/xdoc-documentation-language-for-eclipse.html
- ... (add others)
18.10.2011 10:41:05 (de.abg.reichert.joerg): provided documentation infrastructure based on WikiText with commit fd6ab3b9b363d54f3fb60e087544a4e49e625252
As documentation is an on going I close this issue.
- stakeholder: Spray user
- keywords: Type: Task
- status: DONE

## issue0037
Remove "extension" keyword
04.10.2011 07:02:44 (karsten.thoms): The language already depends heavily on looking up the GenModel for referred EClasses. From the GenModel the associated file extension can be derived, thus the &quot;extension&quot; keyword is not required.
04.10.2011 07:18:37 (karsten.thoms): Extended GenModelHelper
Refactored metamodel, grammar & template code
- stakeholder: Spray user
- keywords: Type: Enhancement, Priority: Medium
- status: DONE

## issue0038
The referenced package 'http://www.eclipse.org/xtext/common/JavaVMTypes' was imported from a different location.
04.10.2011 22:14:18 (Alex.Roldugin): Error in org.eclipselabs.spray.xtext/Spray.xtext with message:
The referenced package 'http://www.eclipse.org/xtext/common/JavaVMTypes' was imported from a different location. Here: 'platform:/plugin/org.eclipse.xtext.common.types/model/JavaVMTypes.ecore
<b>What steps will reproduce the problem?</b>
1. Make dir C:/spray_sources/
2. cd to C:/spray_sources/
3. Make repository clone with command:
git clone https://code.google.com/a/eclipselabs.org/p/spray/
(so after cloning I got only one &quot;spray&quot; directory inside C:/spray_sources/)
4. Open workspace with set path to C:/spray_sources/
5. Import project from spray/releng
6. Set &quot;Spray Target Platform&quot; in Window &gt; Preferences &gt; Plugin-Development &gt; Target Platform
7. Import all projects from spray/plugins/
8. After projects auto-building and refreshing I got several errors in Spray.xtext - main of which described above
<b>What is the expected output? What do you see instead?</b>
I expect to see no errors after projects' building
<b>What version of the product are you using? On what operating system?</b>
I use eclipse with info:
&quot;Eclipse Modeling Tools
Version: Indigo Release
Build id: 20110615-0604&quot;
<b>Please provide any additional information below.</b>
If I build with:
mvn clean install -Pskip-ui-tests
all works perfectly
04.10.2011 22:18:20 (Alex.Roldugin): Repository Commit:eb21786a6220b763416ce6298fa63efa1902540a
10.11.2011 06:58:07 (karsten.thoms): The error mentioned above does not occur anymore. References in the metamodel and genmodel are using NS URIs now, we had some platform URIs there. The Grammar also uses only NS URI, which is recommended from Xtext 2.1.0 on.
However, another error is shown, which is likely a Xtext bug. Opened issue#70 to track this one.
- stakeholder: Spray user
- keywords: Type: Defect, Priority: Medium
- status: DONE

## issue0039
Use spray.target in the build
05.10.2011 18:36:12 (karsten.thoms): Tycho resolves its dependencies from the P2 repositories configured by the &lt;repository&gt; entries in the parent pom.
The spray.target target definition file defines the target platform as well. The build should use this definition, this reduces the risk of using different targets in development and build.
06.10.2011 00:19:54 (karsten.thoms): Changed parent POM and added POM for the target definition
- stakeholder: Spray user
- keywords: Type: Task, Component: Build
- status: DONE

## issue0040
Error in code generation of CreateConnectionFeatures array in feature provider
05.10.2011 21:19:30 (Alex.Roldugin): <b>What steps will reproduce the problem?</b>
1. Create spray project with wizard and use default settings
2. Use attached spray-file to generate code
3. Look at MyDiagramFeatureProviderBase::getCreateConnectionFeatures. In my case it looks like this:
public ICreateConnectionFeature[] getCreateConnectionFeatures() {
return new ICreateConnectionFeature[] { ,,
};
}
If we add one more shape description (e.g. for BusinessDomainModel's EClass) we will see not two commas, but three. If one more - four commas, and so on.
<b>What version of the product are you using? On what operating system?</b>
Eclipse Modeling Tools
Version: Indigo Release
Build id: 20110615-0604
Windows XP SP3
06.10.2011 00:32:10 (karsten.thoms):
06.10.2011 01:19:48 (karsten.thoms): This issue was closed by revision fd948e39a176.
06.10.2011 01:32:36 (karsten.thoms): Note that the "extension" keyword was removed, it is derived from the genmodel now.
- stakeholder: Spray user
- keywords: Type: Defect, Priority: Medium
- status: DONE

## issue0041
Upgrade to Tycho 0.13.0
06.10.2011 00:19:06 (karsten.thoms): Tycho 0.13.0 was released.
Release notes see: http://wiki.eclipse.org/Tycho/Release_Notes/0.13
Upgraded POM.
- stakeholder: Spray user
- keywords: Type: Task, Component: Build
- status: DONE

## issue0042
Nested shapes
08.10.2011 20:04:29 (Alex.Roldugin): In Add/CreateSomethingFeature we have ability to override canAdd/canCreate method, so it means that we can change target container from Diagram to other shape. But all spray containers doesn't pay attention to this fact and use Diagram as parent shape for all spray containers (e.g. in SprayRectangleContainer):
public ContainerShape createContainer(IAddContext context,
Object addedModelElement) {
targetDiagram = (Diagram) context.getTargetContainer();
....
}
Is it possible to use ContainerShape as target containers instead of Diagram? Or it's the best (the fastest) way to instantiate my own SprayRectangleContainer-like container in Add/CreateSomethingFeature's constructor?
18.10.2011 15:03:10 (joswarmer): This is an enhancement, not a defect.
05.11.2011 17:14:23 (joswarmer): We currently do not have nested contasiners in Sparey., so it is correct to add allcontai8ners to the diagram. It is be a useful enhancement to have nested containers. Once we have them this need to change.
28.09.2012 09:12:32 (joswarmer): While adding compartyments to the shapes, addingnested shapes is an easy thing to do as well. Will taake this up.
30.09.2012 21:08:27 (joswarmer):
19.11.2012 15:00:56 (joswarmer): Fixed when adding compartments.
- stakeholder: Spray user
- keywords: Priority: Medium, Type: Enhancement
- status: DONE

## issue0043
Compilation errors in wizard-generated project
09.10.2011 13:02:23 (refsdal.ivar): <b>What steps will reproduce the problem?</b>
1. Install Spray from CI build.
2. Create a new project using the wizard.
3. Change the contents of the .spray file to the following:
diagram mydiagram2
// Add import statements here, e.g.
import BusinessDomainDsl.*
class BusinessClass:
container ( fill=dark_green )
[
// text ( ) { &quot;&lt;&lt;&quot;+eClass.name+&quot;&gt;&gt; &quot; + name};
]
4. Save the file.
<b>What is the expected output? What do you see instead?</b>
A clean compile. Instead one gets:
Description Resource Path Location Type
IColorConstant cannot be resolved to a variable Mydiagram2AddBusinessClassFeatureBase.java /org.eclipselabs.spray.examples.mydiagram2/src-gen/org/eclipselabs/spray/examples/mydiagram2/features line 65 Java Problem
If you add this line:
text ( ) { &quot;&lt;&lt;&quot;+eClass.name+&quot;&gt;&gt; &quot; + name};
You will get:
Description Resource Path Location Type
Couldn't resolve reference to JvmIdentifiableElement '+'. mydiagram2.spray /org.eclipselabs.spray.examples.mydiagram2/model line: 18 /org.eclipselabs.spray.examples.mydiagram2/model/mydiagram2.spray Xtext Check (fast)
<b>What version of the product are you using? On what operating system?</b>
Spray CI 0.3.0, Eclipse Indigo MDT SR1 20110916-0149.
<b>Please provide any additional information below.</b>
It would be good with a getting started tutorial.
I suppose things like this should work with proper setup, so I guess I could be doing something wrong..?
09.10.2011 15:52:48 (refsdal.ivar): Solution:
Edit ./plugins/org.eclipselabs.spray.generator.graphiti/src/org/eclipselabs/spray/generator/graphiti/templates/AddShapeFeature.xtend
and add "
import org.eclipse.graphiti.util.IColorConstant;
"
to line 75.
PS: It seems that the current mvn clean install will not detect a changed .xtend file and re-generate the .java file. One must open the .xtend file in Eclipse and save it to make it update, at least that was my experience.
PS2: Is there a recommended way to check out the source code?
I've failed in numerous ways...
09.10.2011 16:07:55 (refsdal.ivar): "by check out the source" I mean to import it into Eclipse and then it should compile without errors or further fixes.
Building from the console in the releng directory works fine.
An example of failure is using "import from Maven projects from SCM " and "https://code.google.com/a/eclipselabs.org/p/spray/" as URL from m2eclipse:
This will complain about not finding:
fornax-oaw-m2-plugin:3.3.0:run-workflow
tycho-packaging-plugin:0.13.0:validate-id
09.10.2011 16:18:00 (jos.warmer@openmodeling.nl): Chnaged Xtend files will not be seen by Maven indeed, the Java files in xtend-gen need to be checked in. This is due to the way Xtend works, it needs the compiled Java classes to generate its own Java, which does not work with Maven.
10.10.2011 13:58:41 (karsten.thoms): This issue was closed by revision 7ed5b95bd93b.
10.10.2011 14:00:38 (refsdal.ivar): Thanks!
10.10.2011 14:02:40 (karsten.thoms): Thanks for reporting!
The "missing" plugins can be fetched from the pluginRepositories configured in releng/pom.xml
<pluginRepositories>
<pluginRepository>
<id>sonatype</id>
<url>http://repository.sonatype.org/content/groups/sonatype-public-grid/</url>
<releases>
<enabled>true</enabled>
</releases>
<snapshots>
<enabled>true</enabled>
</snapshots>
</pluginRepository>
<!-- Fornax Workflow Runner plugin -->
<pluginRepository>
<id>fornax</id>
<url>http://www.fornax-platform.org/m2/repository</url>
<releases>
<enabled>true</enabled>
</releases>
<snapshots>
<enabled>false</enabled>
</snapshots>
</pluginRepository>
</pluginRepositories>
10.10.2011 14:14:59 (refsdal.ivar): Thanks. I figured it was available there too. The problem for me was that
(1. I don't know how to use m2eclipse very well or anything maven related really..)
2. m2eclipse/similar seemingly didn't consult the releng pom.xml when importing some of the plugins.
Importing releng worked OK IIRC, but not all of the others. I suppose simply adding the above once more to the other pom.xmls would solve this...
Somehow I suspect I would not have these problems if I was using itemis' Eclipse bundle..?
- stakeholder: Spray user
- keywords: Type: Defect, Priority: Medium
- status: DONE

## issue0044
Compilation errors in wizard-generated project: Couldn't resolve reference to JvmIdentifiableElement
10.10.2011 18:31:37 (refsdal.ivar): <b>What steps will reproduce the problem?</b>
1. Clean CI install of Spray.
2. Create a new Spray project with the wizard.
3. Edit the .spray file with the following contents:
diagram mydiagram1
import BusinessDomainDsl.*
class BusinessClass:
container ( fill=dark_green )
[
text ( ) { &quot;&lt;&lt;&quot;+eClass.name+&quot;&gt;&gt; &quot; + name};
]
<b>What is the expected output? What do you see instead?</b>
No build errors.
Description Resource Path Location Type
Couldn't resolve reference to JvmIdentifiableElement '+'. mydiagram1.spray /org.eclipselabs.spray.examples.mydiagram1/model line: 25 /org.eclipselabs.spray.examples.mydiagram1/model/mydiagram1.spray Xtext Check (fast)
Couldn't resolve reference to JvmIdentifiableElement '+'. mydiagram1.spray /org.eclipselabs.spray.examples.mydiagram1/model line: 25 /org.eclipselabs.spray.examples.mydiagram1/model/mydiagram1.spray Xtext Check (fast)
Couldn't resolve reference to JvmIdentifiableElement '+'. mydiagram1.spray /org.eclipselabs.spray.examples.mydiagram1/model line: 25 /org.eclipselabs.spray.examples.mydiagram1/model/mydiagram1.spray Xtext Check (fast)
<b>What version of the product are you using? On what operating system?</b>
Spray SDK Feature 0.3.0.201110101215
Errors in both eclipse-SDK-3.7-Xtext-2.0.1-linux-gtk.tar.gz and eclipse-modeling-indigo-SR1-linux-gtk.tar.gz.
<b>Please provide any additional information below.</b>
11.10.2011 09:54:19 (karsten.thoms): The manifest needs to add import package org.eclipse.xtext.xbase.lib
Fixed with
http://code.google.com/a/eclipselabs.org/p/spray/source/detail?r=e2de5f60edbb340af87c929dae8bf30bf3ecbe09
- stakeholder: Spray user
- keywords: Type: Defect, Priority: Medium, Component: Codegen
- status: DONE

## issue0045
Allow usage of genmodel in workspace
11.10.2011 07:58:45 (karsten.thoms): Spray requires that it can look up the Genmodel for a given EClass. Responsible for this is the GenModelHelper. This looks up the map
EcorePlugin.getEPackageNsURIToGenModelLocationMap()
This map will be filled automatically with genmodels registered by extension point. It does not work with Genmodels that are only in the workspace.
For the runtime part, the given GenModelHelper should be sufficient. Additional genmodels must be registered manually, like it is done in the unit tests.
In the UI, a specialized GenModelHelper could add look up from the workspace. To do: Write this specialized GenModelHelper in plugin org.eclipselabs.spray.xtext.ui and bind it to the SprayUiModule.
18.10.2011 10:38:01 (de.abg.reichert.joerg): resolved with commits 4a7a5cc845d840bac2dfa4e81aca8410338a9e88 and 4a7a5cc845d840bac2dfa4e81aca8410338a9e88
28.10.2011 13:11:41 (karsten.thoms): Re-implemented this feature by using a IResourceChangeListener. The new implementation will register all genmodels on startup, on adding, project open.
Added deregistering on project close / resource delete.
Deleted JavaProjectBasedBuilderParticipant2
29.10.2011 09:58:04 (fabio.filippelli): On my workspace i still can not reference to own implemented ecore models (+ genmodels), but the genmodel will be registered and unregistered on the right way (as the console output shows up).
Maybe there is a still an issue with this? Otherwise the steps to add a own implemented ecore model should be add to the user documentation?
30.10.2011 01:13:33 (karsten.thoms): The problem is that the Ecore file must be indexed by Xtext. This does only occur for projects having the Xtext nature. This can be configured from the project's context menu: Configure / Add Xtext Nature.
Extended User Guide.
- stakeholder: Spray user
- keywords: Type: Defect, Priority: Medium
- status: DONE

## issue0046
Couldn't resolve reference to Module 'org.eclipselabs.spray.xtext.generator.SprayGenerator'.
11.10.2011 08:41:08 (karsten.thoms): When having o.e.s.examples.one in the workspace, the workflow SprayGenerator.mwe2 is marked with error
Couldn't resolve reference to Module 'org.eclipselabs.spray.xtext.generator.SprayGenerator'.
The &quot;missing&quot; workflow is located in plugin org.eclipselabs.spray.generator.graphiti, and its package is exported. The plugin is also listed as required bundle.
Missing Dependency? Xtext-Bug?
01.11.2011 07:40:04 (karsten.thoms): An exception is raised:
Caused by: java.lang.ClassCastException: org.eclipse.xtext.common.types.impl.JvmVoidImplCustom cannot be cast to org.eclipse.emf.mwe2.language.mwe2.DeclaredProperty
at org.eclipse.emf.mwe2.language.mwe2.impl.AssignmentImplCustom.getFeatureName(AssignmentImplCustom.java:31)
at org.eclipse.emf.mwe2.language.validation.Mwe2JavaValidator.checkReferables(Mwe2JavaValidator.java:172)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.eclipse.xtext.validation.AbstractDeclarativeValidator$MethodWrapper.invoke(AbstractDeclarativeValidator.java:108)
25.04.2012 18:15:37 (karsten.thoms): Might have to do with issue#127, since the referenced MWE2 workflow is in a linked folder from the dev workspace, which is not indexed.
22.11.2012 16:30:12 (joswarmer): Is this still a problem ?
23.11.2012 16:04:26 (de.abg.reichert.joerg): It still is. But it is just a flaw.
23.11.2012 16:08:57 (de.abg.reichert.joerg): Ok, when adding these dependencies to the MANIFEST.MF of the model project, the markers disappear:
org.eclipselabs.spray.styles;bundle-version="0.5.0",
org.eclipselabs.spray.shapes;bundle-version="0.5.0",
org.eclipselabs.spray.generator.graphiti;bundle-version="0.5.0"
- stakeholder: Spray user
- keywords: Type: Defect, Priority: Low
- status: DONE

## issue0047
mod4j-busmod.properties projectPath not consistent usable in build and in Eclipse
18.10.2011 14:36:54 (de.abg.reichert.joerg): In /Users/ci_server/git/spray/examples/one/org.eclipselabs.spray.examples.one/model/mod4j-busmod.properties the project path must be non relative when used in Eclipse (to enable the build) and relative when used in the Jenkins build (to find the sources).
see commit 9be63b2bcca29da2012cffe8cd8bf3ad037162c0, that reverted the change of commit 4fa13907c5c964932b9beb7410f085a706cb9cbd
18.10.2011 15:01:17 (joswarmer): I'll handle this one. The path should only be used when not inside Eclipse. Within Eclipse we should use the project to find the location for the different folders.
18.10.2011 17:20:41 (joswarmer): Done, projectPath not nused in Eclipse anymore, use eclipse project location instead.
- stakeholder: Spray user
- keywords: Type: Defect, Priority: Medium
- status: DONE

## issue0048
Sign Jars
27.10.2011 09:58:31 (karsten.thoms): The resulting Jars are unsigned. We have to sign them in the build.
27.10.2011 12:07:44 (karsten.thoms): Question: Were to get a key from?
04.11.2011 20:16:53 (karsten.thoms): We would need a valid certificate. We won't get the funding yet.
- stakeholder: Spray user
- keywords: Type: Defect, Priority: Medium, Component: Build
- status: OPEN

## issue0049
Upgrade to Xtext 2.1.0
27.10.2011 11:20:59 (karsten.thoms): Xtext 2.1.0 is about to be released. For Spray it is especially important that the Outlet paths are configurable. Also the Xtend Organize Imports function and builder syntax are useful.
In most sense it will be a drop-in replacement. Only ToolBehaviourProvider.xtend needs a bit refactoring.
The target definition must be adjusted.
04.11.2011 20:17:45 (karsten.thoms): - target platform updated
- project migrated
fixed with 0.4.0 build 139
- stakeholder: Spray user
- keywords: Type: Defect, Priority: Medium
- status: DONE

## issue0050
Palette contains group "XXX"
27.10.2011 14:43:30 (karsten.thoms): The generated Palette contains an entry &quot;XXX&quot;, see screenshot.
This is hard coded in ToolBehaviourProvider.xtend
28.10.2011 08:44:22 (joswarmer):
08.11.2011 09:16:41 (karsten.thoms): Can we consider this one as fixed?
08.11.2011 13:52:43 (joswarmer): Yes :-)
- stakeholder: Spray user
- keywords: Type: Defect, Priority: Medium
- status: DONE

## issue0051
Code is not generated for example project
28.10.2011 10:20:58 (torkildR): &gt;What steps will reproduce the problem?
1. Follow instructions in the documentation for generating &quot;busmod&quot; example project
2. Press finish on the last page of the wizard
&gt;What is the expected output? What do you see instead?
I get four NPEs in org.eclipse.xtext.builder.impl.XtextBuilder. There is no more information.
&gt;What version of the product are you using? On what operating system?
Latest integration build (#125) on 64-bit OS X 10.7
&gt;Please provide any additional information below.
If I after installing the aforementioned build on my development Eclipse start a runtime instance in debug mode I'm actually able to produce code when repeating steps 1 and 2. I don't understand why there is a difference. The target platform is the running platform.
28.10.2011 10:35:11 (joswarmer):
01.11.2011 08:01:35 (karsten.thoms): Verified in development and test environment. In both cases code generation works.
My test environment is a "plain-vanilla" Eclipse 3.7.1 Java IDE. I just updated the Spray SDK feature from the CI update site, followed the tutorial instructions and code was generated successfully.
Please reopen when having more evidence.
- stakeholder: Spray user
- keywords: Type: Defect, Priority: Medium
- status: DONE

## issue0052
Provide possibility to set the file extensions of the businessmodel
31.10.2011 11:42:50 (veit.hoffmann.vh): The Framework should provide the possibility to set the filename of the businessmodel file. Currently the Framework assumes the name specified in the genmodel of the businessmodel. In many situations this is not the case. E.g. if you create a xtext-dsl from the uml-metamodel for class diagrams you typically wouldn't use the file extension uml that is specified in the genmodel.
Karsten Thoms said that this could possibly be handled by adding a field in the properties file.
<b>What version of the product are you using? On what operating system?</b>
V.0.3.x Win 7
01.11.2011 07:35:35 (karsten.thoms): Potentially Spray could potentially map classes from different packages, which would result in different EMF files. It needs to be considered if Spray may be restricted to one, or if the wizard just covers the case to map one EPackage. This would also be the most likely scenario.
Changing to enhancement request.
14.11.2011 23:39:31 (karsten.thoms):
15.11.2011 06:39:00 (karsten.thoms): This issue was closed by revision 8118a112f089.
- stakeholder: Spray user
- keywords: Type: Enhancement, Priority: Medium
- status: DONE

## issue0053
Import org.eclipse.xtext.ecore is missing in graphiti generator
31.10.2011 16:55:47 (joswarmer): The mwe2 file in generator.graphiti refers to EcoreSupport.java from org.eclipse.xtext.ecore, which is missing in the manifest.mf
31.10.2011 16:56:56 (joswarmer):
31.10.2011 17:01:48 (joswarmer):
01.11.2011 06:48:03 (karsten.thoms):
01.11.2011 08:55:39 (karsten.thoms): This issue was closed by revision 1307803f7bd0.
- stakeholder: Spray user
- keywords: Type: Defect, Priority: Critical
- status: DONE

## issue0054
Automatic code generation does not work in runtime eclipse
31.10.2011 17:07:49 (joswarmer): When running spray from a development environemnt into a runtime eclipse, there is no code generation taking place at saving tyhe spary model file
31.10.2011 17:14:25 (joswarmer): Strangely enough, for a new Xtext project it does not work either, despite what is explained in http://kthoms.wordpress.com/2011/09/28/moving-an-xtend-generator-into-its-own-plugin/ . I checked everything, it seems ok, but no code generation is happening at all.
01.11.2011 06:48:50 (karsten.thoms):
01.11.2011 07:25:56 (karsten.thoms): Verified that automatic code generation is triggered in my runtime workspace. Tested on itemis Xtext 2.0.1 distro.
Closing. Reopen when having more insight on the circumstances.
- stakeholder: Spray user
- keywords: Type: Defect, Priority: Critical
- status: DONE

## issue0055
maven clean deletes org.eclipselabs.spray.xtext.jvmmodel.SprayJvmModelInferrer (java class)
01.11.2011 16:17:14 (fabio.filippelli): <b>What steps will reproduce the problem?</b>
1. Checkout Spray Project
2. Execute &quot;mvn clean install&quot;
3. Since project &quot;org.eclipselabs.spray.xtext&quot; is build, it fails because the class org.eclipselabs.spray.xtext.jvmmodel.SprayJvmModelInferrer can not be resolved.
<b>What is the expected output? What do you see instead?</b>
Successfull build was expected, but the maven build fails since project org.eclipselabs.spray.xtext is been tryed to be build.
06.11.2011 23:53:56 (fabio.filippelli): just retested... fixed with new commits
- stakeholder: Spray user
- keywords: Type: Defect, Priority: Medium, Component: Build
- status: DONE

## issue0056
Plugin providers injection as singleton
01.11.2011 18:13:09 (Alex.Roldugin): While plugin activator is singleton, so plugin use the same injector in all opened diagrams.
So if some feature calls through feature provider
getDiagramTypeProvider() = getInstance(IDiagramTypeProvider.class) = Activator.get(IDiagramTypeProvider.class);
it will got the same instance of DiagramTypeProvider, and that's why if we in create feature will call
getDiagram()=getFeatureProvider().getDiagramTypeProvider().getDiagram();
then it will return the same diagram instance.
05.11.2011 17:48:45 (joswarmer): This makes clear that feature provider should not be injected at all.
07.11.2011 08:35:16 (karsten.thoms): True. We have to go back to the original pattern without injection here.
07.11.2011 21:24:31 (joswarmer): Karsten, can you pick this up?
08.11.2011 08:48:18 (karsten.thoms): Will do.
08.11.2011 09:47:21 (karsten.thoms): Removed usage of injection for the provider implementations.
Fixed with revision#ca0d75acf2d2
- stakeholder: Spray user
- keywords: Type: Defect, Priority: Medium
- status: DONE

## issue0057
eContainer should be selectable for connection ends
04.11.2011 09:26:44 (veit.hoffmann.vh): The from and to attribute of a connection should accept eContainer.
This allows modelling connections for which one of the ends is the semantic container. E.g UML Generalization.
class Generalizaton :
connection (width=1) [
from eContainer;
to general;
]
Currently eContainer is not available, since it is an eOperation property of EObject Class and not an eStructuralFeature.
05.11.2011 17:09:36 (joswarmer): If the eContainer should be used this way, there should be a reference from Generalization to the eContainer. If this reference is not in the metamodel it should not be used in the from and to.
08.11.2011 00:12:36 (karsten.thoms): The eContainer is somehow special. It is a kind of implicit reference, and I think it should be possible to specify it as possible end points.
08.11.2011 13:58:02 (joswarmer): The eContainer is special in tyhe sense that it is a necessary implementation property from EMF. If you really want to use the reference to the container in a model you should model it explicitly in your ecore model. This also ensures it gets a proper understandable name. It is bad style to use the eContainer this way.
15.11.2011 13:20:58 (karsten.thoms): I'm not sure anymore and thinking that Jos will be right here. Question is how this should be enabled for what Veit wants to express, namely specifying the connection for an UML Generalization.
Maybe this related to issue#60, where the containment reference into which an element is inserted is specified for the create behavior.
And maybe this makes the 'from' side of a connection optional.
I have to see this in an example.
15.11.2011 19:34:17 (veit.hoffmann.vh): @ 4 I don't think that's wise. One can easily think of a Model where the target of an edge has the container role. Thus you wouldn't gain much by making 'from' optional. I think it is better to make the container property optional, as it is now. This works for all cases where one of the ends has container role. In all other cases one needs to set the container property explicitely.
16.11.2011 11:02:47 (joswarmer): I agree with veit.
22.11.2012 14:04:10 (joswarmer):
- stakeholder: Spray user
- keywords: Type: Task, Priority: Medium
- status: OPEN

## issue0058
A businesselement shold be attachable to Diagrams
04.11.2011 09:30:56 (veit.hoffmann.vh): It should be possible to attach a buisinesselemen to the diagram itself similar to MetaClasses. e.g.
class Model:
diagram(&lt;&lt;some properties&gt;&gt;) [
]
This is needed for a well structured semantic model and if DrillDownFeatures should be supportable at any time.
05.11.2011 17:20:11 (joswarmer): I fully agree that this should be possible.
05.11.2011 17:24:13 (joswarmer): The question is whether this should be done in the DSL , or in the manual extension code. Need to try out how this can be sued.
08.11.2011 00:18:56 (karsten.thoms): Veit will provide a sample implementation for example.one
14.11.2011 22:33:47 (karsten.thoms): This must be a property of the diagram. The project wizard must also offer to specify the model element type.
I am thinking the DSL to look like this:
diagram mydiagram for MyModel
It is also necessary to know the model type to offer containment references for create features.
To shorten the names for the root element type the import statements must occur before the 'diagram' keyword:
{{{
import BusinessDomainDsl.*
diagram mod4j for BusinessDomainModel // imported
}}}
15.11.2011 06:41:02 (karsten.thoms): Committed changes for DSL, Metamodel, Scoping, Templates
The implementation code has to create the Model element now and add created elements to it now.
15.11.2011 12:41:39 (joswarmer): I like this change. A question: should we make it mandatory that a diagram alkways represents one Domain model type ? I think this certainly is good style and makes it much easier to define editors with Graphiti / Spray.
I am in favor of making this mandatory.
15.11.2011 12:57:47 (karsten.thoms): At the moment it is mandatory, I was thinking the opposite way around: Should it be possible that it is optional?
The project wizard inforces you now to choose a root element type. I have preparations pending that the model element is created and elements created into a given containment reference. I think this can make it this week.
See issue#60 for this.
15.11.2011 13:08:40 (joswarmer): I strongly advice not to do this (saves you work as well :-) . It is a sensible restriction to ensure that the diagram always has one Domain element connected at the root. From my experience with using Graphiti / Spray I do have seen that not having a root Domain element for a diagram will make life much more complex at many places.
E.g. solutions for issue http://code.google.com/a/eclipselabs.org/p/spray/issues/detail?id=60 will become more complex, as the context in which to add becomes even more unclear and more difficult to find.
15.11.2011 13:14:28 (karsten.thoms): OK for me. It makes the code also more concise.
15.11.2011 14:23:46 (veit.hoffmann.vh): Sorry I was very busy last week. Do you still need an example implementation for example.one
16.11.2011 00:26:16 (karsten.thoms): Introduced a ModelService template: The ModelService class is responsible for creating the model root and attaching it to a new resource
The URI of the model instance is stored in the diagram for later fetching
Changed the create feature to add an element to its containment reference.
As a further bonus, the model is not saved instantly anymore. Instead the diagram is marked dirty after element creation. If the domain model file does not exist, it will be created on saving.
16.11.2011 00:28:33 (karsten.thoms): @Veit: You may have a look at the new implementation. Does this now fit your requirements?
- stakeholder: Spray user
- keywords: Type: Enhancement, Priority: Medium
- status: DONE

## issue0059
Vertical resize of containers is ignored
04.11.2011 09:34:54 (veit.hoffmann.vh): On resize of a container-Shape the vertical resize is ignored.
This is due to the layout Methode in SprayRectangleContainer that resets the height of the shape to a value calculated from the height of contained texts.
05.11.2011 18:30:12 (joswarmer):
08.11.2011 00:21:27 (karsten.thoms): Layout feature ignores the minimum size
28.09.2012 09:13:16 (joswarmer): A simple copy-paste error in the generator, it generates setHorizontalStrecht(true) twice.
30.09.2012 21:07:52 (joswarmer): Fixed this, it was a copy-paste error in code generation template.
- stakeholder: Spray user
- keywords: Type: Defect, Priority: Low
- status: DONE

## issue0060
Connections should have a container Property
04.11.2011 09:40:42 (veit.hoffmann.vh): It should be possible to set the container of a connection.
e.g.
class usecasedescriptionmodel.Inclusion:
connection (width=1) [
from includingUC;
to includedUC;
container includingUC.eContainer;
]
This is similar to bug 42 and different from bug 57, since this behavior is only nesseary for connections whose businesselement is not contained in one of the ends businesselements.
05.11.2011 17:21:18 (joswarmer): Right, if one of the ends is the container this is not needed, but otherwise the container need to be specified.
05.11.2011 17:21:38 (joswarmer):
05.11.2011 17:22:56 (joswarmer):
08.11.2011 00:29:52 (karsten.thoms): Its not the container that could be set, it must be the containment feature
container includingUC.eContainer.properties
public Connection create(ICreateConnectionContext context) {
Connection newConnection = null;
// get EClasses which should be connected
BusinessClass source = getBusinessClass(context.getSourceAnchor());
// TODO: add source to containment feature
14.11.2011 22:31:57 (karsten.thoms): After thinking a bit about this the right position to specify is the create behavior. When an object is created, it must be added to a containment reference of the current container. So far we only allow one level of containment, but this will change likely with nested shapes.
A first approach is to change the DSL like this:
class BusinessClass :
...
behavior {
create into types
}
The scope of the possible references are the containment references of the container type (for a MetaClass it is the Model type for the Diagram, see also issue#58).
The given reference must be used to assign the newly created object in the CreateFeature.
16.11.2011 00:24:20 (karsten.thoms): This issue was closed by revision d8a225023394.
16.11.2011 00:27:32 (karsten.thoms): With this commit, an element is created into a given containment reference.
- stakeholder: Spray user
- keywords: Type: Defect, Priority: Medium
- status: DONE

## issue0061
Custom Figures
04.11.2011 10:01:21 (veit.hoffmann.vh): Appart from standard figures other than rectangle like ellipse. The Framework should support custom figures. E.g. the uml Actor figure.
class Actor : container ( fill = dark_green ) [
customFigure &lt;&lt;ClassName&gt;&gt;;
...
]
I'm not sure how this can be implemented on source code level, but maybe a mechanism similar to SprayRectangleContainer can be used. I.e. aceptable custom figure classes should extend an abstract class/ interface that defines the methods needed by the framework for rendering.
05.11.2011 17:22:20 (joswarmer): Also, we should provide some more standard figures.
05.11.2011 17:22:45 (joswarmer):
07.11.2011 11:54:26 (de.abg.reichert.joerg): We could do offer three figure reference types
* proposals for the existing Graphiti shapes like Rectangle, RoundedRectangle, Ellipse
(with configuration some how: width, height, degree of rounded corners)
* reference to custom figure implementation classes in the classpath (implementation must implement a certain interface)
* reference to figure specification in DSL: Polygones may be defined like (0,0)-(0,1)-(1,1)-(1,0) - we could build up a default DSL figure library that is shipped with Spray by default
Beside the definition of shape figures we would also need some default connection decorator figures, some pre defined arrow styles for the connection ends like -> or -|> or -<>.
With use of the Label provider or the Documentation provider we could even provide a preview of the figures in the DSL, either by using a reference to an icon file or even more sophisticated by calculating the preview by the coordinates of the figure (SVG like).
07.11.2011 21:22:07 (joswarmer): I will start with the first and second one (existing Graphiti figures, and an interface to implement). I will leave the third option (create a DSL for shapes) for now.
08.11.2011 13:40:09 (veit.hoffmann.vh): I really like the third idea in comment 3.
Maybe one could define layout of coposite figures in a model like that.
I.e. one could define how parts of a figure behave on resize similar to how this is done in a forms oriented framework.
To the idea of a preview. one could use the preview of graphity by generating an in memory model. I will investigate this a little more soon.
25.03.2012 23:58:46 (fabio.filippelli): Point 2 and 3 implemented in the Shape DSL (marker interface as well).
08.10.2012 19:46:26 (joswarmer): Fixed by the Shape DSL and option to refer to custom Java figures
- stakeholder: Spray user
- keywords: Type: Enhancement, Priority: Medium
- status: DONE

## issue0062
Spray Editor must close when project closes
07.11.2011 11:09:56 (karsten.thoms): Steps to reproduce
1) Open a Spray model file
2) Close the project in the Package Explorer
=&gt; Model file stays open
07.11.2011 11:15:33 (karsten.thoms): This issue was closed by revision 4d01d77a3c7d.
07.11.2011 11:16:21 (karsten.thoms): Changed in SprayMultiPageEditor: Implementing IResourceChangeListener to close the editor on closing the project.
07.11.2011 14:18:12 (karsten.thoms): Need also to close the editor when the project is deleted
07.11.2011 14:18:58 (karsten.thoms): This issue was closed by revision 75a50bb85694.
- stakeholder: Spray user
- keywords: Type: Defect, Priority: Medium
- status: DONE

## issue0063
Files generated into folder with project name
07.11.2011 11:43:00 (karsten.thoms): Steps to reproduce:
- Create a new Spray project with the wizard
=&gt; generated files will go into a folder named with the project name, see screenshot
07.11.2011 12:35:22 (karsten.thoms): This issue was closed by revision a049970ed011.
- stakeholder: Spray user
- keywords: Type: Defect, Priority: Medium
- status: DONE

## issue0064
SprayUserGuide.pdf Install introduction update sites url wrong
07.11.2011 22:42:18 (bernhard.merkle): For the latest release:
- is not documented in the PDF (but somewhere in the wiki)
For the latest stable build:
- the url is wrong.
currently in the doc:
https://spray.ci.cloudbees.com/job/spray-ci-build/lastSuccessfulBuild/artifact/releng/repository/target/repository/
it should be:
https://spray.ci.cloudbees.com/job/spray-ci-build/lastSuccessfulBuild/artifact/releng/org.eclipselabs.spray.repository/target/repository/
08.11.2011 08:05:01 (karsten.thoms):
08.11.2011 08:18:18 (karsten.thoms): This issue was closed by revision 9ca6b0f50a19.
- stakeholder: Spray user
- keywords: Type: Defect, Priority: Medium
- status: DONE

## issue0065
SprayUserGuide.pdf: Choose the Diagram Type "busmod"
07.11.2011 23:27:39 (bernhard.merkle): Choose the Diagram Type &quot;busmod&quot;
it is not there. There is &quot;mod4j&quot; however..
08.11.2011 08:04:35 (karsten.thoms): "mod4j" comes from the example project for the same metamodel, which is installed with the SDK. "busmod" should be there definetely if you have chosen this as the last part of the project name as described.
I am pretty sure that this works. I will try again with installing the latest build.
09.11.2011 11:37:04 (de.abg.reichert.joerg): I think it is because of the old plugin.xml. The name of the diagram is stated there. Initially the project is generated with mod4j is used in plugin.xml. I think this is the actual problem. If you change the diagram name in the DSL than this is generated to src-gen/plugin.xml. This plugin.xml have to be copied over the plugin.xml in the project root to apply the diagram name change.
09.11.2011 13:04:01 (karsten.thoms): The initially generated plugin.xml should be copied after finishing the project wizard. Thus, it should also contain the diagram type provider. Could you confirm again that this does not work for you?
09.11.2011 17:41:02 (de.abg.reichert.joerg): with latest 0.0.4-SNAPSHOT, doing it exactly like described in the documentation, the busmod is set as diagram type. So this works for me.
09.11.2011 21:16:49 (karsten.thoms):
- stakeholder: Spray user
- keywords: Type: Defect, Priority: Medium
- status: DONE

## issue0066
Language should use curly brackets
09.11.2011 13:19:10 (karsten.thoms): The Spray Language uses [] for block statements.
I got user feedback that this seems intuitive, and curly brackets {} are preferred. Also, when we make use of expressions, we already have the curly brackets in the language for XBlockExpression.
Therefore I propose to change this.
09.11.2011 17:50:53 (karsten.thoms):
09.11.2011 22:07:31 (karsten.thoms):
09.11.2011 22:18:32 (karsten.thoms): - changed Spray.xtxt
- changed sample .spray files
- fixed unit tests
- changed template.xml
- changed project wizard template
- stakeholder: Spray user
- keywords: Type: Defect, Priority: Medium, Component: Language
- status: DONE

## issue0067
Develop Shape DSL
09.11.2011 20:50:42 (karsten.thoms): Spray needs to be able to define custom shapes, and nested shapes. However, this should not clutter the &quot;core&quot; language.
Thus, Spray needs another language which addresses the definition of Shapes. This could look something like this:
===================================================
class BusinessClass:
shape BpmnMail
{
text ( ) { &quot;&lt;&lt;&quot;+eClass.name+&quot;&gt;&gt; &quot; + name};
line ( color=black width=2 );
reference properties attribute dataType;
line (width=2 color=RGB(255,138,141));
reference businessRules; // will use name property by default
line (width=2 color=IColorConstant::DARK_BLUE);
text () &quot;::&quot; + description;
line (width=1 ) ;
}
--------------------------------------------------
// In a separate file:
shape BpmnMail {
ellipse(width=100, heigth=100, linestyle=normal) {
rectangle(x=10, y=25, width=80, heigth=50) {
polygon(point=(0,0), point=(25,40), point=(0,40))
}
}
}
===================================================
The base project name could be
org.eclipselabs.spray.shapes
It should not only possible to define Shapes in a DSL and generate the implementation, also implementing them in Java and referring to them through JVM types should be possible.
In long term, a preview would be helpful, but for now this is postponed.
28.11.2011 13:50:08 (veit.hoffmann.vh): I really love this idea.
Moreover i think the dsl should allow the description of behavior on resize.
A rather lightweigth approach would be to have fix and relative sizes and positions
e.g.
shape BpmnMail {
ellipse(width=100, heigth=100, linestyle=normal) {
rectangle(x=10%, y=25, width=80%, heigth=50) {
...
}
}
}
A number meaning "fix" and a percentage meaning "resizes with parent"
Alternatively on could have a full fledged way to describe sizes relative to any other part of the figure similar to FormLayout in swt.
(see http://www.eclipse.org/articles/article.php?file=Article-Understanding-Layouts/index.html)
22.01.2012 10:44:29 (fabio.filippelli): Task is started and first version already commited.
25.03.2012 23:57:37 (fabio.filippelli): Already implemented (online).
- stakeholder: Spray user
- keywords: Type: Task
- status: DONE

## issue0068
Improve default look and feel
09.11.2011 21:41:47 (karsten.thoms): Currently the resulting editors don't look good by default. We don't have margins, gradients, shadows etc. which would make the editor more &quot;sexy&quot;. In order to gain attention, the results that Spray produces must be improved.
22.01.2012 10:42:52 (fabio.filippelli): Task is started and first version already commited.
25.03.2012 23:57:47 (fabio.filippelli): Already implemented (online).
- stakeholder: Spray user
- keywords: Type: Task
- status: DONE

## issue0069
Add aliases for Shape elements
09.11.2011 22:23:43 (karsten.thoms): We need to define names for Shape elements (line, text etc.). The name is optional.
These names should be used to define variable and method names for the shape elements that are created in the code templates. This makes it easier to identify these elements in the code.
09.11.2011 22:23:53 (karsten.thoms):
14.11.2011 08:07:45 (karsten.thoms): This issue was closed by revision 65dd70ab3d24.
- stakeholder: Spray user
- keywords: Type: Enhancement, Priority: Medium, Component: Language
- status: DONE

## issue0070
Xtext Grammar shows error Cannot find compatible feature type in sealed EClass
10.11.2011 06:55:32 (karsten.thoms): The Xtext grammar shows errors, but it does not affect the functionality. The grammar can be translated.
Reported as bug for Xtext:
https://bugs.eclipse.org/bugs/show_bug.cgi?id=363421
10.11.2011 21:02:45 (karsten.thoms): Got some online help from Sebastian Zarnekow luckily.
It is important that Ecore.ecore is not in the workspace. This was the case for the unit tests. Removed Ecore.ecore and Ecore.genmodel from the workspace.
Next, in the spray.genmodel the feature "Initialize by loading" was set to true for the Spray GenPackage. This caused that a spray.ecore was produced into the impl package, and SprayPackageImpl#initialize() loaded that file. Set this flag to false now.
Refactored GenModelHelperTest to test against BusinessDomainDsl.genmodel instead of Ecore.genmode.
10.11.2011 21:03:33 (karsten.thoms): This issue was closed by revision 7ffbcada295c.
- stakeholder: Spray user
- keywords: Type: Defect, Priority: Medium, Component: Language
- status: DONE

## issue0071
Fix alias for metaclasses
10.11.2011 09:20:27 (joswarmer): Spray supports aliases like:
class BusinessClass alias Interface :
to allow multiple shape representations for one metclass.
However, currently thr is a validation that checks for uniqueness of the class name in these onstructs, effectively making this feature impossible to use. The validation needs to be adjusted.
10.11.2011 10:46:13 (joswarmer): Hmmm, I tried a bit last night. Adding an alias to a meta class works fine and generates all features with the alias name. But ... as soon as I use the same meta class twice with an alias I get the following errors while running the code generator. This seems to be broken when the meta class changed to becoming a real reference to an EClass.
0 [main] INFO lipse.emf.mwe.utils.StandaloneSetup - Registering platform uri 'D:\spray\gitclone\spray'
1911 [main] INFO clipse.emf.mwe.utils.GenModelHelper - Registered GenModel 'http://www.mod4j.org/busmod' from 'platform:/resource/org.mod4j.dsl.businessdomain.mm/model/BusinessDomainDsl.genmodel'
2154 [main] INFO lipse.emf.mwe.utils.StandaloneSetup - Adding generated EPackage 'org.eclipselabs.spray.mm.spray.SprayPackage'
5946 [main] ERROR mf.mwe2.launch.runtime.Mwe2Launcher - Problems running workflow org.eclipselabs.spray.example.one.SprayGenerator: Validation problems:
8 errors:
mod4j-busmod.spray - D:\spray\gitclone\spray\examples\one\org.eclipselabs.spray.examples.one\model\mod4j-busmod.spray
null: Duplicate JvmAnnotationTarget '<unnamed>'
java.lang.RuntimeException: Problems running workflow org.eclipselabs.spray.example.one.SprayGenerator: Validation problems:
8 errors:
mod4j-busmod.spray - D:\spray\gitclone\spray\examples\one\org.eclipselabs.spray.examples.one\model\mod4j-busmod.spray
null: Duplicate JvmAnnotationTarget '<unnamed>'
at org.eclipse.emf.mwe2.launch.runtime.Mwe2Runner.run(Mwe2Runner.java:99)
at org.eclipse.emf.mwe2.launch.runtime.Mwe2Runner.run(Mwe2Runner.java:73)
at org.eclipse.emf.mwe2.launch.runtime.Mwe2Runner.run(Mwe2Runner.java:64)
at org.eclipse.emf.mwe2.launch.runtime.Mwe2Runner.run(Mwe2Runner.java:55)
at org.eclipse.emf.mwe2.launch.runtime.Mwe2Launcher.run(Mwe2Launcher.java:74)
at org.eclipse.emf.mwe2.launch.runtime.Mwe2Launcher.main(Mwe2Launcher.java:35)
Caused by: org.eclipse.emf.mwe.core.WorkflowInterruptedException: Validation problems:
8 errors:
mod4j-busmod.spray - D:\spray\gitclone\spray\examples\one\org.eclipselabs.spray.examples.one\model\mod4j-busmod.spray
null: Duplicate JvmAnnotationTarget '<unnamed>'
at org.eclipse.xtext.mwe.Validator.validate(Validator.java:89)
at org.eclipse.xtext.mwe.Reader.invokeInternal(Reader.java:165)
at org.eclipse.emf.mwe.core.lib.AbstractWorkflowComponent.invoke(AbstractWorkflowComponent.java:126)
at org.eclipse.emf.mwe.core.lib.Mwe2Bridge.invoke(Mwe2Bridge.java:34)
at org.eclipse.emf.mwe.core.lib.AbstractWorkflowComponent.invoke(AbstractWorkflowComponent.java:201)
at org.eclipse.emf.mwe2.runtime.workflow.AbstractCompositeWorkflowComponent.invoke(AbstractCompositeWorkflowComponent.java:35)
at org.eclipse.emf.mwe2.runtime.workflow.AbstractCompositeWorkflowComponent.invoke(AbstractCompositeWorkflowComponent.java:35)
at org.eclipse.emf.mwe2.runtime.workflow.Workflow.run(Workflow.java:19)
at org.eclipse.emf.mwe2.launch.runtime.Mwe2Runner.run(Mwe2Runner.java:97)
... 5 more
10.11.2011 18:56:43 (karsten.thoms):
10.11.2011 19:24:21 (karsten.thoms): This issue was closed by revision 2b5ad7790a29.
- stakeholder: Spray user
- keywords: Type: Task
- status: DONE

## issue0072
Improve formatter for the Spray DSL
10.11.2011 17:20:57 (de.abg.reichert.joerg): the initial org.eclipselabs.spray.xtext.formatting.SprayFormatter wraps not all lines correctly
14.11.2011 09:37:45 (de.abg.reichert.joerg):
15.11.2011 14:17:05 (de.abg.reichert.joerg): made my changes, so CTLR + SHFT + F should produce an acceptable output.
I am still undecided, how to handle the layout properties section, maybe we should introduce commas, to make it more readable
version 1: current version with spaces before and after =, the properties cannot be distingished so good
( color = dark_green fill = dark_blue )
version 2: version without spaces before and after =, might be to narrow
( color=dark_green fill=dark_blue )
version 1: current version with spaces before and after = and two spaces between properties, so the properties cant be distingished better, unfortunately I did not get the formatter to do that
( color = dark_green fill = dark_blue )
16.11.2011 15:26:38 (karsten.thoms): When inserting a block expression for a text element, the expression should be rendered in one line. Usually these expressions should not necessarily be that complex.
fromText text ( ) { fromCardinality};
-> formatted:
fromText text ( ) {
fromCardinality
};
29.03.2012 15:50:24 (karsten.thoms): The formatter has already been improved a lot. Can we close this one for now and reopen it when we have concrete issues of the formatter?
29.03.2012 22:14:40 (de.abg.reichert.joerg): We can close it, I had not found a solution, how to do formatting dependent on the use context of the rule, but when you have already fix it, we can close it.
- stakeholder: Spray user
- keywords: Type: Enhancement, Priority: Low
- status: DONE

## issue0073
Class is regenerated in src-gen although it has been moved to src before
10.11.2011 17:27:06 (de.abg.reichert.joerg): I tested this for the add feature as well as for custom feature, so it is a basic problem.
Tested on commit 2fdf2afde133b48d944edab81a855082cc372c53.
18.11.2011 02:48:15 (karsten.thoms): JavaGenFile#extensionFileExists does not prefix the project path for the file path. Need access to the IProject of the EclipseResourceFileSystemAccessExt. Implementing IAdaptable for this.
18.11.2011 10:24:12 (karsten.thoms): This issue was closed by revision 5cf205373e56.
- stakeholder: Spray user
- keywords: Type: Defect, Priority: Medium
- status: DONE

## issue0074
Properties View does not work anymore
10.11.2011 17:35:17 (de.abg.reichert.joerg): Whether for nodes, attributes nor connections the properties view is shown, although the classes *Filter and *NameSection are generated.
Tested for commit 2fdf2afde133b48d944edab81a855082cc372c53.
10.11.2011 20:57:04 (de.abg.reichert.joerg): strangely the current revision works under Ubuntu, in Windows 7 it doesn't
11.11.2011 15:47:28 (joswarmer): I will take a look next week
13.11.2011 16:27:22 (de.abg.reichert.joerg): I found my mistake: I forgot to copy the regenerated plugin.xml from src-gen to the root of the project. So the generated properties view extensions could not take effekt.
- stakeholder: Spray user
- keywords: Type: Defect, Priority: High
- status: DONE

## issue0075
alias specification not applied to property classes generation
10.11.2011 17:43:00 (de.abg.reichert.joerg): in the Spray DSL you can state something like that:
class State alias Zustand :
container ( )
{
text ( ) { name };
}
behavior {
create palette &quot;PaletteName&quot;;
}
The in the feature package those classes are generated:
* Mydiagram1AddZustandFeature
* Mydiagram1CreateZustandFeature
* and so on
But in the property package the classes still have the name:
* StateFilter
* StateNameSection
I first thought this causes the problem of #74 , but it doesn't. So this may only flaw.
19.11.2012 13:44:29 (joswarmer): There is opnly one property sheet for a domain class, therefore all aliases can use the property sheet of their domain class. There is no need for a separate property sheet for an alias.
- stakeholder: Spray user
- keywords: Type: Defect, Priority: Medium
- status: DONE

## issue0076
Layout application not appropriate
10.11.2011 18:18:52 (de.abg.reichert.joerg):
I know, that the Layout will be refatored soon, but as long as this has not happend the current way should be improved, so that the user are not confused:
Actually I think there are multiple issues:
* when I press for code completion in container ( _ ) then I get proposed: bold, color, figure, fill, italic, witdh
* bold: only makes sense for fonts, of should it be interpreted as global style for the hole container?
* color: same as bold
* italic: same as bold
* figure: not interpreted in the generator, should be cleaned up as long as it is not supported to not disturb early adopters
* fill: generates this
GraphicsAlgorithm containerGa = containerShape.getGraphicsAlgorithm();
containerGa.setBackground(manageColor(0, 0, 160));
but is not visible in the diagram - actually I do not think this is the right place to set the background color, this should be only done to PictogramElements like Rectangles, Text and so on. In Graphiti a ContainerShape as well as a Shape are only logical elements that group visible elements.
* as said already in fill, ContainerShape as Shape are only logical elements, that will grab their height and width in dependence of the dimension and positions of its visible elements.
Conclusion: In all places where attributes are allowed, all types of attributes are proposed, although only a subset is sensible. Some of the attributes are even not supported yet and should be left out as long as they are not supported.
* container ( ): can't think of any reasonable attribute yet
* text ( ): only bold, color, fill, italic are sensible - the width should be calculated by the font/style/size + text length (there is a Graphiti operation for that), but maybe despite of that the width is still necessary; figure is not useful for text, should be left out; the fill attribute is actually not applied in the diagram
* connection: width, color
* rectangle: not supported yet, should be left out at all
* line: width, color
Currently the background color can never be applied, as there is a rectangle keyword, but the generator of the Add feature does not generate any code. A figure is currently only build up from Texts and Lines. So there is no common background color, as the container is just a logical element and no rectangle is created in the Add feature.
10.11.2011 18:19:23 (de.abg.reichert.joerg):
19.11.2012 15:04:26 (joswarmer): This old way of doing containers is now replaced by the compartments integrated into the shape DSL. This issue is therefore not relevant anymore.
- stakeholder: Spray user
- keywords: Type: Enhancement, Priority: Low
- status: DONE

## issue0077
Palette definition not intuitive
10.11.2011 18:37:02 (de.abg.reichert.joerg): When I first defined a diagram editor in the Spray DSL, I wrote something like that:
class State :
container ( )
{
text ( ) { name };
}
Then I opened the diagram editor and wondered, that there is no palette. I found out, that I have to define additionally
behavior {
create palette &quot;PaletteName&quot;;
}
I think this counterintuitive. First, an entry in the palette is essential. By default Graphiti defines the compartments Objects and Connections and put nodes in Objects and References in Connections. The Spray Generator always overrides the IPaletteCompartmentEntry[] getPalette() method in the ToolBehaviourProviderBase, so if you forget to define the palette, you get surprised.
That the palette is managed as a behavior is a technical aspect of Graphiti and is not obvious to the user.
I would suggest defining palette this way:
paletteCompartments {
classes alias &quot;The classes&quot;
references alias &quot;The references&quot;
}
class State :
paletteCompartment classes
container ( )
{
text ( ) { name };
}
If there is no palette compartments defined the getPalette() in ToolBehaviourProviderBase should not be overridden or at least the code in the overridden method should call super.getPalette().
This is just a proposal, have your thoughts on it.
10.11.2011 18:44:34 (de.abg.reichert.joerg): Just a side note, the referenced attributes types there seems no way to define the palette compartment, they are always placed in a compartment named Create. With my proposal, you can write that:
paletteCompartments {
...
attributes alias "The attributes"
}
class ...:
container ... {
...
reference actions attribute name palette attributes
}
- stakeholder: Spray user
- keywords: Type: Enhancement, Priority: Low
- status: OPEN

## issue0078
References should only be allowed to containment features
10.11.2011 18:56:01 (de.abg.reichert.joerg):
example domain model:
model
cont. states
ref. action
cont actions
When you then use actions,
class State: ...
reference actions attribute name
the add of the action will fail in the diagram, as it is not contained in a resource. So either the DSL should validate, that a containment reference is used or in the generated diagram editor code it should only be allowed to add elements that have been already created in their container.
model
cont. states
cont action
Would work with the existing Spray.
If you model it in the Spray DSL like that
class State: ...
reference actions attribute name
class Action ...
and than create the action first as node and then try to add an action as attribute reference to the state node, this also fails in the current Spray.
11.11.2011 15:52:40 (joswarmer): This looks very much like the same problem as http://code.google.com/a/eclipselabs.org/p/spray/issues/detail?id=60 . Non containment references could be allowed if we have the ability to specify their container, this would b the same solution as described in the other issue.
15.11.2011 13:15:54 (karsten.thoms): I'll take that, since I'm working on issue#60. I am about to implement the scoping rules for this.
15.11.2011 13:37:31 (joswarmer): Right Karsten, if you resolve #60, this one will be resolved as well.
16.11.2011 08:35:02 (karsten.thoms): This issue was closed by revision a8a3457b2f59.
- stakeholder: Spray user
- keywords: Type: Defect, Priority: Medium
- status: DONE

## issue0079
Provide ability of semantic validation in the diagrams
10.11.2011 20:02:12 (de.abg.reichert.joerg):
In Graphiti you can use decorators, e.g. add a warn or error marker to an element in the diagram when it violates certain semantic rules.
Spray should support such validations. The validation rules could be defined either
* in generated Java gap classes or
* in the Spray DSL itself or
* if the domain model is Xtext based, their Java Validator might be reused
For defining decorators, the DefaultToolBehaviorProvider.getDecorators(PictogramElement pe) can be used.
29.11.2011 21:29:10 (karsten.thoms): With issue#93 XtextValidationDecoratorProvider is introduced. It implements the newly added interface IRenderingDecoratorProvider, which can be used from Spray specific tool behavior providers.
- stakeholder: Spray user
- keywords: Type: Enhancement, Priority: Low
- status: OPEN

## issue0080
Metamodel Cleanup
10.11.2011 21:28:18 (karsten.thoms): The following types are not used anymore:
- MetaAttribute
- StringLiteral
- VisibleElement
- SprayString
Remove these elements and refactor occurances in the code.
11.11.2011 18:46:26 (karsten.thoms): Renaming
MetaReference#reference
-> MetaReference#target
Templates have some ugly "reference.reference" constructs. This looks a bit confusing. Renaming to "target" is more concise.
14.11.2011 05:55:02 (karsten.thoms): Fixed with commit 5b2f196d8ca4
- stakeholder: Spray user
- keywords: Type: Task, Priority: Medium
- status: DONE

## issue0081
Upgrade to Xtext 2.1.1
11.11.2011 12:43:04 (karsten.thoms): Today Xtext 2.1.1 will be released. I had a talk with Sebastian Zarnekow yesterday. Xtext 2.1.0 had some issues that made this early bugfix release necessary. So far I did not face any severe problems, but Sebastian warmly recommended to upgrade to 2.1.1.
15.11.2011 13:01:16 (karsten.thoms): Joerg, I noticed that you updated already the target definition. I'm assigning the task to you.
15.11.2011 14:10:22 (de.abg.reichert.joerg): yes, I tried loading the old target in my Eclipse, but it refuses, claiming, it cannot resolve the 2.1.0 version of Xtext, so I raised the version to 2.1.1. I did not encounter any problems so far, no further changes in the code had to be done.
So I think this task is fixed.
- stakeholder: Spray user
- keywords: Type: Task
- status: DONE

## issue0082
Rename Behaviour to Behavior
14.11.2011 08:29:29 (karsten.thoms): Currently we have a mixture of &quot;Behaviour&quot; (British English) and &quot;Behavior&quot; (American English) in the grammar and metamodel. We should stick to one alternative, namely American English.
15.11.2011 07:40:57 (karsten.thoms): fixed with commit #8118a112f089
- stakeholder: Spray user
- keywords: Type: Defect, Priority: Medium
- status: DONE

## issue0083
Spray UI Activator does not start when genmodel cannot be registered
14.11.2011 16:59:10 (karsten.thoms): During the plugin activation of the SprayActivator the workspace is scanned for genmodels to register them. It can be that a NPE occurs in MWE's GenModelHelper in line 64, when a GenPackage contains an unresolvable proxy. The occuring NPE is not catched, which causes that the UI does not start.
In class RegisterPlatformGenmodelListener also RuntimeExceptions must be caught to at least continue the startup process.
14.11.2011 17:00:06 (karsten.thoms): This issue was closed by revision c268b2acdff3.
- stakeholder: Spray user
- keywords: Type: Defect, Priority: Medium
- status: DONE

## issue0084
default package name in Spray project wizard
15.11.2011 12:36:06 (de.abg.reichert.joerg): When you change the default project name to your own project name on the first wizard page, then the second wizard package should use this name for the base package name.
15.11.2011 14:10:48 (de.abg.reichert.joerg):
15.11.2011 23:42:35 (karsten.thoms):
16.11.2011 00:42:50 (karsten.thoms): This issue was closed by revision a439b73ce266.
- stakeholder: Spray user
- keywords: Type: Defect, Priority: Low
- status: DONE

## issue0085
Model EClass wizard
15.11.2011 12:37:15 (de.abg.reichert.joerg): ModelEclass generates for section in DSL but does not generate the import needed for that element
15.11.2011 14:07:18 (de.abg.reichert.joerg): ok, my mistake, the import statement is generated properly, in my situation
import org.eclipse.xtext.example.fowlerdsl.statemachine.*
But when using an element from that namespace, the element cannot be found:
diagram statecharts for Statemachine
When removing this diagram statement leaving only the import statement, the import statement is marked with this error message:
The required feature 'modelType' of 'org.eclipselabs.spray.mm.spray.impl.DiagramImpl@3bbd6a{platform:/resource/org.eclipselabs.spray.examples.statecharts/model/statecharts.spray#/}'
must be set
16.11.2011 07:38:44 (karsten.thoms):
16.11.2011 15:06:15 (karsten.thoms): As workaround try the following:
1) Make sure the project containing the metamodel has the Xtext nature
2) Look into Navigate / Open Model Element if you can find an EClass from that package there
3) Make sure that the .ecore and .genmodel files are on a Java source folder
4) import the EPackage name, not the Java package of the generated EPackage.
import statemachine.*
Does this work for you?
18.11.2011 20:45:26 (de.abg.reichert.joerg): the 4) worked for me, I have to use
import statemachine.*
instead of the pre generated
import org.eclipse.xtext.example.fowlerdsl.statemachine.*
of the Spray wizard.
20.11.2011 18:05:26 (de.abg.reichert.joerg): fixed generation of import statement by loading the model resource, looking for an EClass that name matches the chosen root class in the wizard and fetches the name of its containing EPackage. The full qualified name of the chosen class is not interpreted so, so there may cases where classes with same simple name exist in multiple packages.
- stakeholder: Spray user
- keywords: Type: Defect, Priority: Medium
- status: DONE

## issue0086
Please explain, how to support Graphiti default shapes
15.11.2011 14:32:33 (de.abg.reichert.joerg):
Currently there is already a rule Rectangle in the Spray DSL, but the generator does not handle it yet. I naively tried to implement a further dispatch createShape operation for type Rectangle, but ended up with a lot of compilation errors in other parts of the generated code.
There is lot of registrations and setting properties, I did not understand. For creating good looking diagrams (color gradients and so on), at least the default shapes should be supported. But for that, there must exist an understanding, how the code works and how the code can be (in first sight manually) extended to introduce rectangles.
def dispatch createShape (Rectangle rectangle) '''
«val varname = rectangle.shapeName.toFirstLower»
// Part is Rectangle
{
String type = &quot;«rectangle.fullyQualifiedName»&quot;;
// create shape for text and set text graphics algorithm
Shape «varname» = peCreateService.createShape(textContainer, false);
Rectangle rectangle = gaService.createRectangle(getDiagram());
rectangle.setBackground(manageColor(«rectangle.lineColor»));
rectangle.setForeground(manageColor(«rectangle.fillColor»));
gaService.setLocationAndSize(rectangle, 0, 0, 0, 0);
peService.setPropertyValue(«varname», &quot;MODEL_TYPE&quot;, type);
peService.setPropertyValue(«varname», ISprayContainer.CONCEPT_SHAPE_KEY, ISprayContainer.RECTANGLE);
// create link and wire it
link(«varname», addedModelElement);
}
'''
28.11.2011 10:17:29 (veit.hoffmann.vh): Hi Jörg,
for making a Rectangle show it must have a size greater than zero.
gaService.setLocationAndSize(rectangle, context.getX(), context.getY(),
width, height);
with height= context.getHeight() <= 0 ? 50 : context.getHeight();
You can do that in the Layout feature also!
Besides you should draw all shapes of a figure onto one ContainerShape. I attached an example of an AddFeature that creates a figure containing two nested rectangels an a centered direct editable text.
28.11.2011 10:44:33 (de.abg.reichert.joerg): Hi Veit,
you are right, setting the dimension to 0 is bad idea and instead of using textContainer I should use containerShape:
ContainerShape containerShape = container.createContainer(context, addedModelElement);
ContainerShape textContainer = SprayContainerService.findTextShape(containerShape);
This is issue #86 is concerned about the right usage of the Spray runtime classes.
When I used the code above in the generator this had produced non compiling code.
Last week I (re-)discovered http://code.google.com/a/eclipselabs.org/p/spray/source/browse/plugins/org.eclipselabs.spray.runtime.graphiti/src/org/eclipselabs/spray/runtime/graphiti/containers/
So there already predefined shapes shipped with Spray and in the code you see how to interact with SprayContainerService, so most of my questions are answered.
I have seen in your code that you use the setters of the font object, this actual not a good idea:
http://www.eclipse.org/forums/index.php/m/710593/#msg_710593
https://bugs.eclipse.org/bugs/show_bug.cgi?id=355347
28.11.2011 11:48:15 (veit.hoffmann.vh): Hi Jörg,
thanks for pointing out the issue with the font. We will change this.
Cheers
Veit
12.11.2012 17:58:03 (joswarmer):
- stakeholder: Spray user
- keywords: Type: Task, Priority: Medium
- status: OPEN

## issue0087
Build fails while testing
15.11.2011 18:23:27 (fabio.filippelli): -------------------------------------------------------
T E S T S
-------------------------------------------------------
Running org.eclipselabs.spray.xtext.tests.Mod4jTest
0 [main] INFO lipse.emf.mwe.utils.StandaloneSetup - Registering platform uri 'C:\Users\FFI\git\spray\tests'
EMMA: collecting runtime coverage data ...
3635 [main] INFO s.xtext.utils.unittesting.XtextTest - testing mod4j/mod4j-busmod.spray in test method Mod4jTest.test_mod4j_busmod
Tests run: 1, Failures: 0, Errors: 0, Skipped: 0, Time elapsed: 5.908 sec
Running org.eclipselabs.spray.xtext.tests.ValidationRulesTest
5471 [main] INFO s.xtext.utils.unittesting.XtextTest - testing validation/alias-02.spray in test method ValidationRulesTest.test_alias_02
5652 [main] INFO s.xtext.utils.unittesting.XtextTest - testing validation/alias-01.spray in test method ValidationRulesTest.test_alias_01
5739 [main] DEBUG s.unittesting.FluentIssueCollection - line 7: Duplicate SprayElement '&lt;unnamed&gt;' / classpath:///validation/alias-01.spray#/0/@met
aClasses.0/@representedBy/@parts.0
5739 [main] DEBUG s.unittesting.FluentIssueCollection - line 8: Duplicate SprayElement '&lt;unnamed&gt;' / classpath:///validation/alias-01.spray#/0/@met
aClasses.0/@representedBy/@parts.1
5739 [main] DEBUG s.unittesting.FluentIssueCollection - line 8: Duplicate alias name line1 / classpath:///validation/alias-01.spray#/0/@metaClasses
.0/@representedBy/@parts.1
5740 [main] DEBUG s.unittesting.FluentIssueCollection - line 7: Duplicate SprayElement '&lt;unnamed&gt;' / classpath:///validation/alias-01.spray#/0/@met
aClasses.0/@representedBy/@parts.0
5740 [main] DEBUG s.unittesting.FluentIssueCollection - line 8: Duplicate SprayElement '&lt;unnamed&gt;' / classpath:///validation/alias-01.spray#/0/@met
aClasses.0/@representedBy/@parts.1
Tests run: 2, Failures: 1, Errors: 0, Skipped: 0, Time elapsed: 0.844 sec &lt;&lt;&lt; FAILURE!
Running org.eclipselabs.spray.xtext.util.GenModelHelperTest
5753 [main] INFO lipse.emf.mwe.utils.StandaloneSetup - Registering platform uri 'C:\Users\FFI\git\spray\tests\org.eclipselabs.spray.xtext.tests'
5861 [main] WARN clipse.emf.mwe.utils.GenModelHelper - There is already a GenModel registered for NamespaceURI 'http://www.mod4j.org/busmod'. It wil
l be overwritten from 'classpath:/mod4j/BusinessDomainDsl.genmodel' to 'platform:/resource/org.eclipselabs.spray.xtext.tests/model/mod4j/BusinessDomai
nDsl.genmodel'
5862 [main] INFO clipse.emf.mwe.utils.GenModelHelper - Registered GenModel 'http://www.mod4j.org/busmod' from 'platform:/resource/org.eclipselabs.sp
ray.xtext.tests/model/mod4j/BusinessDomainDsl.genmodel'
Tests run: 6, Failures: 0, Errors: 0, Skipped: 0, Time elapsed: 0.724 sec
EMMA: runtime coverage data merged into [C:\Users\FFI\git\spray\tests\org.eclipselabs.spray.xtext.tests\coverage.ec] {in 43 ms}
Results :
Failed tests: test_alias_01(org.eclipselabs.spray.xtext.tests.ValidationRulesTest): &lt;no id&gt; failed
Tests run: 9, Failures: 1, Errors: 0, Skipped: 0
15.11.2011 23:19:49 (karsten.thoms): same error on CI:
[https://spray.ci.cloudbees.com/job/spray-ci-build/org.eclipselabs.spray$org.eclipselabs.spray.xtext.tests/159/testReport/org.eclipselabs.spray.xtext.tests/ValidationRulesTest/test_alias_01/]
15.11.2011 23:41:50 (karsten.thoms): This issue was closed by revision aba77a88823f.
16.11.2011 10:08:08 (fabio.filippelli): The build is still failing.
[INFO] --- fornax-oaw-m2-plugin:3.3.0:run-workflow (generate) @ org.eclipselabs.spray.examples.one ---
[INFO] Fornax Model Workflow Maven2 Plugin V3.3.0
[ERROR] org.eclipse.emf.mwe2.launch.runtime.Mwe2Launcher - Problems running workflow org.eclipselabs.spray.example.one.SprayGenerator: Validation pr
blems:
[ERROR] 1 error:
[ERROR] mod4j-busmod.spray - C:\Users\FFI\git\spray\examples\one\org.eclipselabs.spray.examples.one\model\mod4j-busmod.spray
[ERROR] 25: Couldn't resolve reference to EReference 'superclass'.
[ERROR] java.lang.RuntimeException: Problems running workflow org.eclipselabs.spray.example.one.SprayGenerator: Validation problems:
[ERROR] 1 error:
[ERROR] mod4j-busmod.spray - C:\Users\FFI\git\spray\examples\one\org.eclipselabs.spray.examples.one\model\mod4j-busmod.spray
[ERROR] 25: Couldn't resolve reference to EReference 'superclass'.
[ERROR] at org.eclipse.emf.mwe2.launch.runtime.Mwe2Runner.run(Mwe2Runner.java:99)
[ERROR] at org.eclipse.emf.mwe2.launch.runtime.Mwe2Runner.run(Mwe2Runner.java:73)
[ERROR] at org.eclipse.emf.mwe2.launch.runtime.Mwe2Launcher.run(Mwe2Launcher.java:76)
[ERROR] at org.eclipse.emf.mwe2.launch.runtime.Mwe2Launcher.main(Mwe2Launcher.java:35)
[ERROR] Caused by: org.eclipse.emf.mwe.core.WorkflowInterruptedException: Validation problems:
[ERROR] 1 error:
[ERROR] mod4j-busmod.spray - C:\Users\FFI\git\spray\examples\one\org.eclipselabs.spray.examples.one\model\mod4j-busmod.spray
[ERROR] 25: Couldn't resolve reference to EReference 'superclass'.
[ERROR] at org.eclipse.xtext.mwe.Validator.validate(Validator.java:89)
[ERROR] at org.eclipse.xtext.mwe.Reader.invokeInternal(Reader.java:165)
[ERROR] at org.eclipse.emf.mwe.core.lib.AbstractWorkflowComponent.invoke(AbstractWorkflowComponent.java:126)
[ERROR] at org.eclipse.emf.mwe.core.lib.Mwe2Bridge.invoke(Mwe2Bridge.java:34)
[ERROR] at org.eclipse.emf.mwe.core.lib.AbstractWorkflowComponent.invoke(AbstractWorkflowComponent.java:201)
[ERROR] at org.eclipse.emf.mwe2.runtime.workflow.AbstractCompositeWorkflowComponent.invoke(AbstractCompositeWorkflowComponent.java:35)
[ERROR] at org.eclipse.emf.mwe2.runtime.workflow.AbstractCompositeWorkflowComponent.invoke(AbstractCompositeWorkflowComponent.java:35)
[ERROR] at org.eclipse.emf.mwe2.runtime.workflow.Workflow.run(Workflow.java:19)
[ERROR] at org.eclipse.emf.mwe2.launch.runtime.Mwe2Runner.run(Mwe2Runner.java:97)
[ERROR] ... 3 more
[ERROR] ExitStatusException occurred while running workflow: Java returned: 1
16.11.2011 10:44:06 (karsten.thoms): sorry, my fault.
This is a scoping problem introduced while fixing issue#78
16.11.2011 11:14:19 (karsten.thoms): should be fixed now; waiting for next build
16.11.2011 11:54:50 (karsten.thoms):
- stakeholder: Spray user
- keywords: Type: Defect, Priority: Medium, OpSys-Windows
- status: DONE

## issue0088
New Spray Project Wizard and files without an extension
16.11.2011 13:32:10 (Ultra30000): <b>What steps will reproduce the problem?</b>
1. Create a new file without an extension (like SVN uses)
2. Try to create a new Spray Project (New -&gt; Other... -&gt; Spray Project -&gt; Next)
3. Exception:
The selected wizard could not be started.
Plug-in org.eclipselabs.spray.xtext.ui was unable to load class org.eclipselabs.spray.xtext.ui.SprayExecutableExtensionFactory.
An error occurred while automatically activating bundle org.eclipselabs.spray.xtext.ui (896).
The problem may be, that IFile.getFileExtension() can return null but is used with .equals()
(like in: org.eclipselabs.spray.xtext.ui.wizard.MetamodelSelectionComposite.widgetSelected() )
16.11.2011 14:17:52 (karsten.thoms): OK, reproducable.
16.11.2011 14:21:33 (karsten.thoms): A NPE occurs in RegisterPlatformGenmodelListener#handleResource(), as described due to the missing file extension. Changed the comparison condition.
16.11.2011 14:22:13 (karsten.thoms): This issue was closed by revision 3dd2a136f4bf.
16.12.2011 15:35:31 (janreimone): I recently installed spray via update site. As I wanted to create a new spray project I got the following error:
"The selected wizard could not be started.
Plug-in org.eclipselabs.spray.xtext.ui was unable to load class org.eclipselabs.spray.xtext.ui.SprayExecutableExtensionFactory.
An error occurred while automatically activating bundle org.eclipselabs.spray.xtext.ui (690)."
So it's exactly the same as posted above but with another number at the end. I first thought that's because I don't have Xtext installed, so I installed it. But the error stays :( How can I create a Spray project?
16.12.2011 15:37:52 (janreimone): addition: I looked into the error log and found this root exception:
Root exception:
org.eclipse.emf.common.util.BasicEList$BasicIndexOutOfBoundsException: index=0, size=0
at org.eclipse.emf.common.util.BasicEList.get(BasicEList.java:352)
at org.eclipselabs.spray.xtext.ui.internal.RegisterPlatformGenmodelListener.registerEPackage(RegisterPlatformGenmodelListener.java:150)
at org.eclipselabs.spray.xtext.ui.internal.RegisterPlatformGenmodelListener.handleResource(RegisterPlatformGenmodelListener.java:96)
at org.eclipselabs.spray.xtext.ui.internal.RegisterPlatformGenmodelListener$3.visit(RegisterPlatformGenmodelListener.java:79)
...
16.12.2011 15:56:44 (karsten.thoms): Will have a look at it.
07.02.2012 13:33:51 (Matthias.Vianden): I have the same issue. When I try to create a spray project (latest stable release - 0.3.0) via the wizard I get the following exception:
The selected wizard could not be started.
Plug-in org.eclipselabs.spray.xtext.ui was unable to load class org.eclipselabs.spray.xtext.ui.SprayExecutableExtensionFactory.
An error occurred while automatically activating bundle org.eclipselabs.spray.xtext.ui (1945).
29.03.2012 20:13:18 (karsten.thoms): Please retry with 0.4.0. I cannot reproduce it here.
If it still exists, please attach the full stack. Best as a file.
13.04.2012 13:28:38 (janreimone): I will try it. Do I have to use the release or the build update site?
13.04.2012 14:35:07 (janreimone): It works now with update site of current release.
- stakeholder: Spray user
- keywords: Type: Defect, Priority: Medium
- status: DONE

## issue0089
Copy generated plugin.xml to project root until deactivated
16.11.2011 15:21:16 (karsten.thoms): When starting with a new project, the plugin.xml is generated to the src-gen folder. It must be manually copied and merged to the project root.
Usually during start up of a project it is not required to make manual changes, so the plugin.xml should be overwritten by default, until this feature is deactivated.
This should be either be configured through the Spray properties file, or by leveraging Output configurations. This may also be combined, so that the runtime OutputConfigurationProvider evaluates the Spray properties file.
02.09.2012 11:29:11 (de.abg.reichert.joerg): there should be a property in properties file (and an option in the project creation wizard before):
override.plugin.xml
with possible values:
* yes: always overridden by each generation
* no: never overridden by each generation
* ask: show a confirmation dialog to the user to let him decide whether to override the file - this dialog should be only shown if the new plug-in.xml would differ from the existing one
27.01.2013 11:19:09 (de.abg.reichert.joerg): alternative solution: http://5ise.quanxinquanyi.de/2013/01/11/avoiding-manual-merge-when-generating-plugin-xml-with-xtextxtend/?utm_source=rss&utm_medium=rss&utm_campaign=avoiding-manual-merge-when-generating-plugin-xml-with-xtextxtend
19.05.2013 15:48:12 (de.abg.reichert.joerg): This issue was closed by revision 6bf2795fa2f4.
- stakeholder: Spray user
- keywords: Type: Defect, Priority: Medium
- status: DONE

## issue0090
Add Spray to Eclipse Marketplace
16.11.2011 17:18:54 (karsten.thoms): In order to get more installations of Spray the project should be integrated into the Eclipse Marketplace.
According to the news there are already over 1 Million software installations done through the Marketplace.
[http://www.heise.de/open/meldung/Ueber-1-Million-Installationen-ueber-den-Eclipse-Marketplace-1377957.html]
- stakeholder: Spray user
- keywords: Type: Task, Priority: Medium
- status: OPEN

## issue0091
Evaluate ZEST Layout Feature
23.11.2011 19:02:06 (karsten.thoms): Joerg pointed me to a forum thread, where a user has implemented a LayoutFeature based on the ZEST visualization framework:
http://www.eclipse.org/forums/index.php/mv/msg/262250/757201/#msg_757201
Attached to the thread is the source of the class.
If the LayoutFeature turns out to be useful it should be added to the graphiti runtime plugin. This would also require extending the target platform by ZEST.
I need exactly something like this for a customer project to initialize a Spray based diagram from a model file.
23.11.2011 22:50:35 (karsten.thoms): This basically works, but I think we have to evolve it a bit. The feature does layout a whole diagram. This should also be possible with a selection.
What needs to be thought of is whether this feature should be outsourced into a seperate plugin, since it is the only reason for a dependency to Zest, maybe
org.eclipselabs.spray.runtime.graphiti.zest
25.11.2011 09:54:07 (karsten.thoms): Added new plugin and integrated Zest SDK into target platform.
Done with build#184
The feature has to be tested now a bit.
25.11.2011 11:07:22 (karsten.thoms): Added the plugin to the features.
Added documentation to new Cookbook section of the User Guide.
29.11.2011 21:08:16 (karsten.thoms): Zest plugin has been added. For further issues other issue reports should be opened.
- stakeholder: Spray user
- keywords: Type: Enhancement, Priority: Medium
- status: DONE

## issue0092
Split CI builds
25.11.2011 12:34:06 (karsten.thoms): With build#185 we have exceeded the maximum build time of 2000 minutes per month for our builds. A build already takes 40 minutes now.
We have to find ways to reduce the build time again, presumably by splitting the builds.
For example, the building of the Spray repository takes quite a while, since the repository is already &gt; 170 MB large.
Next problem is long startup time, since resolution of the target platform is slow. We should consume a local built target platform instead of the remote repositories.
25.11.2011 12:39:49 (karsten.thoms):
27.11.2011 09:22:55 (de.abg.reichert.joerg):
27.11.2011 09:32:58 (de.abg.reichert.joerg): see also http://groups.google.com/group/spray-dev/browse_thread/thread/fee6a584d9b51374
things to do:
* create extra branch (in future own repository) to hold the P2 repository project containing own the 3rd library dependencies
* introduce new parent pom for P2 repository project and old parent pom
* switch old parent pom to use build P2 repository from Jenkins build job artifact URL
* introduce Maven profiles to be able switch between remote P2 repository and local P2 repository (to be able to work off-line locally)
* investigate means how to configure Git and/or Jenkins to build only the changed Maven projects and their dependent projects (and when found the means apply them)
* update documentation if necessary
13.04.2012 11:39:20 (de.abg.reichert.joerg): * spray-ci-targetplatform: takes 32 minutes, runs midnight and only then when there are changes in the target platform
* spray-ci-build: takes 14 minutes, runs when there are changes in the plug-in projects, checks this every 45 minutes
* spray-docs-build: takes 5 minutes, runs midnight and only then when there are changes in the docs projects
* spray-assembly-build: takes 25 minutes, runs midnight and only then when there are changes
For more details to the build jobs the this message:
http://groups.google.com/group/spray-dev/browse_thread/thread/481cee877019fb28
16.04.2012 10:53:07 (karsten.thoms): Good job!
How did you configure that builds are only triggered on changes to specific subpaths in the repository?
16.04.2012 13:38:48 (de.abg.reichert.joerg): I did not configure that yet, but it is possible - see the attached screenshot.
16.04.2012 13:40:46 (karsten.thoms): Will you configure this later?
16.04.2012 13:45:21 (de.abg.reichert.joerg): Yes, this would be reasonable.
- stakeholder: Spray user
- keywords: Type: Task, Priority: Medium
- status: DONE

## issue0093
Introduce runtime plugin for Xtext related extensions
29.11.2011 21:11:11 (karsten.thoms): Xtext (UI) related runtime classes (features, tool extensions) should be implemented in a new plugin
org.eclipselabs.spray.runtime.graphiti.xtext
First features to add:
- Open Model Element custom feature
- Xtext validation decorator renderer
29.11.2011 21:15:14 (karsten.thoms): This issue was closed by revision 3092b5617824.
- stakeholder: Spray user
- keywords: Type: Enhancement
- status: DONE

## issue0094
Use xtend-maven-plugin, remove xtend-gen sources from repository,
09.12.2011 08:10:48 (karsten.thoms): Xtext 2.2.0 introduces a Maven plugin to compile Xtend sources. This allows finally to remove xtend-gen sources from the repository and let them generate during the build.
For more details see
http://www.eclipse.org/Xtext/xtend/documentation/index.html#MavenSupport
http://kthoms.wordpress.com/2011/12/08/xtext-2-2-finally-brings-maven-support-for-xtend/
TODO:
Evaluate the plugin for Spray and introduce it in the build. Delete generated Java classes from the repository when possible.
02.04.2012 00:37:15 (karsten.thoms): The Xtend Maven Plugin 2.2.1 could not handle multiple source directories. This was fixed for Xtend 2.3.0, but the plugin is closely tied to the Xtend version and is also not available yet on any public repository.
I have backported the current development state to Xtend 2.2.1 and named the version 2.2.2. This version has been deployed to the Fornax repository.
The build now uses the Maven plugin for all plugins with xtend-gen folders. Generated files have been removed from the repository and .gitignore files have been placed into the folder.
The build now runs without any generated sources checked in.
- stakeholder: Spray user
- keywords: Type: Enhancement, Priority: Medium, Component: Build
- status: DONE

## issue0095
Upgrade to Xtext 2.2.0
09.12.2011 18:51:46 (karsten.thoms): Xtext 2.2.0 has been released on Dec 7th and brings direct support for generating Xtend sources with Maven.
<b>TODO:</b>
- Update Target Platform
- Update dependencies in Manifest files
- Update Dev Guide
- Fix upcoming migration issues
13.12.2011 10:44:39 (karsten.thoms): Finished
- stakeholder: Spray user
- keywords: Type: Task
- status: DONE

## issue0096
name in source.name cannot be resolved anymore
11.12.2011 11:07:29 (de.abg.reichert.joerg): This error might be result of the migration to Xtext 2.2.0:
error message
found unasserted issues Issues: - ERROR at XMemberFeatureCall( line 39): Couldn't resolve reference to JvmIdentifiableElement 'name'.
Stacktrace
junit.framework.AssertionFailedError:
found unasserted issues Issues:
- ERROR at XMemberFeatureCall( line 39): Couldn't resolve reference to JvmIdentifiableElement 'name'.
at junit.framework.Assert.fail(Assert.java:47)
at org.eclipselabs.xtext.utils.unittesting.XtextTest.after(XtextTest.java:160)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.junit.runners.model.FrameworkMethod$1.runReflectiveCall(FrameworkMethod.java:44)
at org.junit.internal.runners.model.ReflectiveCallable.run(ReflectiveCallable.java:15)
at org.junit.runners.model.FrameworkMethod.invokeExplosively(FrameworkMethod.java:41)
at org.junit.internal.runners.statements.RunAfters.evaluate(RunAfters.java:37)
at org.eclipse.xtext.junit4.XtextRunner$1.evaluate(XtextRunner.java:55)
at org.eclipselabs.xtext.utils.unittesting.XtextRunner2$1.evaluate(XtextRunner2.java:36)
at org.junit.runners.BlockJUnit4ClassRunner.runNotIgnored(BlockJUnit4ClassRunner.java:79)
at org.junit.runners.BlockJUnit4ClassRunner.runChild(BlockJUnit4ClassRunner.java:71)
at org.junit.runners.BlockJUnit4ClassRunner.runChild(BlockJUnit4ClassRunner.java:49)
at org.junit.runners.ParentRunner$3.run(ParentRunner.java:193)
at org.junit.runners.ParentRunner$1.schedule(ParentRunner.java:52)
at org.junit.runners.ParentRunner.runChildren(ParentRunner.java:191)
at org.junit.runners.ParentRunner.access$000(ParentRunner.java:42)
at org.junit.runners.ParentRunner$2.evaluate(ParentRunner.java:184)
at org.junit.internal.runners.statements.RunBefores.evaluate(RunBefores.java:28)
at org.junit.runners.ParentRunner.run(ParentRunner.java:236)
at org.apache.maven.surefire.junit4.JUnit4TestSet.execute(JUnit4TestSet.java:53)
at org.apache.maven.surefire.junit4.JUnit4Provider.executeTestSet(JUnit4Provider.java:123)
at org.apache.maven.surefire.junit4.JUnit4Provider.invoke(JUnit4Provider.java:104)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.apache.maven.surefire.util.ReflectionUtils.invokeMethodWithArray(ReflectionUtils.java:164)
at org.apache.maven.surefire.booter.ProviderFactory$ProviderProxy.invoke(ProviderFactory.java:110)
at org.apache.maven.surefire.booter.SurefireStarter.invokeProvider(SurefireStarter.java:172)
at org.apache.maven.surefire.booter.SurefireStarter.runSuitesInProcessWhenForked(SurefireStarter.java:104)
at org.apache.maven.surefire.booter.ForkedBooter.main(ForkedBooter.java:70)
Standard Ausgabe (STDOUT)
0 [main] INFO lipse.emf.mwe.utils.StandaloneSetup - Registering platform uri 'C:\Jenkins\workspace\Spray\tests'
EMMA: collecting runtime coverage data ...
3267 [main] INFO s.xtext.utils.unittesting.XtextTest - testing mod4j/mod4j-busmod.spray in test method Mod4jTest.test_mod4j_busmod
4282 [main] WARN s.xtext.utils.unittesting.XtextTest - ---- Unasserted Issues ----
4282 [main] DEBUG s.unittesting.FluentIssueCollection - ERROR at XMemberFeatureCall( line 39): Couldn't resolve reference to JvmIdentifiableElement 'name'.
As workaround one can remove the .name reference as done below:
class Association icon &quot;connection16.gif&quot;:
connection ()
{
from source;
to target;
// fromText text() &quot;source &quot; + source.name;
fromText text() &quot;source &quot; + source;
connectionText text() targetMultiplicity.name;
toText text() name;
}
behavior {
create into associations palette &quot;Connections&quot;;
group samen;
}
11.12.2011 11:13:55 (de.abg.reichert.joerg):
11.12.2011 21:52:14 (karsten.thoms): Observed the same, was also upgrading to Xtext 2.2. I'll analyze this.
12.12.2011 23:58:57 (karsten.thoms): This issue was closed by revision f68ec2ca85f0.
- stakeholder: Spray user
- keywords: Type: Defect, Priority: Medium
- status: DONE

## issue0097
Creating a new project with Spray Wizard fails because RegisterPlatformGenmodelListener is null
11.12.2011 11:13:14 (de.abg.reichert.joerg): Creating a new project with Spray Wizard fails because
@Inject
private RegisterPlatformGenmodelListener registerPlatformGenmodelListener;
is null in org.eclipselabs.spray.xtext.ui.internal.SprayActivatorExt
so in ResourcesPlugin.getWorkspace().addResourceChangeListener(registerPlatformGenmodelListener);
a null listener is passed (that causes then a NPE elsewhere).
As (always with injection) I do not know where RegisterPlatformGenmodelListener is expected to be bound.
This error might be a result of the migration to Xtext 2.2.0, as there the support for support for multi page editors is introduced and we still use our own solution and this might conflict with the resource loading.
11.12.2011 11:14:03 (de.abg.reichert.joerg):
11.12.2011 11:17:35 (de.abg.reichert.joerg): the stack trace (part 1):
Plug-in org.eclipselabs.spray.xtext.ui was unable to load class org.eclipselabs.spray.xtext.ui.SprayExecutableExtensionFactory.
An error occurred while automatically activating bundle org.eclipselabs.spray.xtext.ui (912).
at org.eclipse.xtext.resource.DefaultLocationInFileProvider.getSignificantTextRegion(DefaultLocationInFileProvider.java:38)
at org.eclipse.xtext.ui.editor.folding.DefaultFoldingRegionProvider.computeObjectFolding(DefaultFoldingRegionProvider.java:103)
at org.eclipse.xtext.ui.editor.folding.DefaultFoldingRegionProvider.computeObjectFolding(DefaultFoldingRegionProvider.java:86)
at org.eclipse.xtext.ui.editor.folding.DefaultFoldingRegionProvider.doGetFoldingRegions(DefaultFoldingRegionProvider.java:68)
at org.eclipse.xtext.ui.editor.folding.DefaultFoldingRegionProvider$1.exec(DefaultFoldingRegionProvider.java:60)
at org.eclipse.xtext.ui.editor.folding.DefaultFoldingRegionProvider$1.exec(DefaultFoldingRegionProvider.java:1)
at org.eclipse.xtext.util.concurrent.AbstractReadWriteAcces.readOnly(AbstractReadWriteAcces.java:32)
at org.eclipse.xtext.ui.editor.model.XtextDocument.readOnly(XtextDocument.java:78)
at org.eclipse.xtext.ui.editor.folding.DefaultFoldingRegionProvider.getFoldingRegions(DefaultFoldingRegionProvider.java:56)
at org.eclipse.xtext.ui.editor.folding.DefaultFoldingStructureProvider.calculateProjectionAnnotationModel(DefaultFoldingStructureProvider.java:114)
at org.eclipse.xtext.ui.editor.folding.DefaultFoldingStructureProvider.initialize(DefaultFoldingStructureProvider.java:58)
at org.eclipse.xtext.ui.editor.folding.DefaultFoldingStructureProvider.handleProjectionEnabled(DefaultFoldingStructureProvider.java:99)
at org.eclipse.xtext.ui.editor.folding.DefaultFoldingStructureProvider$ProjectionChangeListener.projectionEnabled(DefaultFoldingStructureProvider.java:186)
at org.eclipse.jface.text.source.projection.ProjectionViewer.fireProjectionEnabled(ProjectionViewer.java:489)
at org.eclipse.jface.text.source.projection.ProjectionViewer.enableProjection(ProjectionViewer.java:537)
at org.eclipse.jface.text.source.projection.ProjectionViewer.doOperation(ProjectionViewer.java:1441)
at org.eclipse.xtext.ui.editor.XtextEditor.installFoldingSupport(XtextEditor.java:471)
at org.eclipse.xtext.ui.editor.XtextEditor.createPartControl(XtextEditor.java:453)
at org.eclipse.ui.internal.EditorReference.createPartHelper(EditorReference.java:670)
at org.eclipse.ui.internal.EditorReference.createPart(EditorReference.java:465)
at org.eclipse.ui.internal.WorkbenchPartReference.getPart(WorkbenchPartReference.java:595)
at org.eclipse.ui.internal.EditorAreaHelper.setVisibleEditor(EditorAreaHelper.java:271)
at org.eclipse.ui.internal.EditorManager.setVisibleEditor(EditorManager.java:1459)
at org.eclipse.ui.internal.EditorManager$5.runWithException(EditorManager.java:972)
at org.eclipse.ui.internal.StartupThreading$StartupRunnable.run(StartupThreading.java:31)
at org.eclipse.swt.widgets.RunnableLock.run(RunnableLock.java:35)
at org.eclipse.swt.widgets.Synchronizer.runAsyncMessages(Synchronizer.java:135)
at org.eclipse.swt.widgets.Display.runAsyncMessages(Display.java:4140)
at org.eclipse.swt.widgets.Display.readAndDispatch(Display.java:3757)
at org.eclipse.ui.application.WorkbenchAdvisor.openWindows(WorkbenchAdvisor.java:803)
at org.eclipse.ui.internal.Workbench$33.runWithException(Workbench.java:1595)
at org.eclipse.ui.internal.StartupThreading$StartupRunnable.run(StartupThreading.java:31)
at org.eclipse.swt.widgets.Synchronizer.syncExec(Synchronizer.java:180)
at org.eclipse.ui.internal.UISynchronizer.syncExec(UISynchronizer.java:150)
at org.eclipse.swt.widgets.Display.syncExec(Display.java:4683)
at org.eclipse.ui.internal.StartupThreading.runWithoutExceptions(StartupThreading.java:94)
at org.eclipse.ui.internal.Workbench.init(Workbench.java:1590)
at org.eclipse.ui.internal.Workbench.runUI(Workbench.java:2623)
at org.eclipse.ui.internal.Workbench.access$4(Workbench.java:2494)
at org.eclipse.ui.internal.Workbench$7.run(Workbench.java:674)
at org.eclipse.core.databinding.observable.Realm.runWithDefault(Realm.java:332)
at org.eclipse.ui.internal.Workbench.createAndRunWorkbench(Workbench.java:667)
at org.eclipse.ui.PlatformUI.createAndRunWorkbench(PlatformUI.java:149)
at org.eclipse.ui.internal.ide.application.IDEApplication.start(IDEApplication.java:123)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:344)
at org.eclipse.core.runtime.adaptor.EclipseStarter.run(EclipseStarter.java:179)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.eclipse.equinox.launcher.Main.invokeFramework(Main.java:622)
at org.eclipse.equinox.launcher.Main.basicRun(Main.java:577)
at org.eclipse.equinox.launcher.Main.run(Main.java:1410)
at org.eclipse.equinox.launcher.Main.main(Main.java:1386)
Caused by: org.osgi.framework.BundleException: Exception in org.eclipselabs.spray.xtext.ui.internal.SprayActivatorExt.start() of bundle org.eclipselabs.spray.xtext.ui.
at org.eclipse.osgi.framework.internal.core.BundleContextImpl.startActivator(BundleContextImpl.java:734)
at org.eclipse.osgi.framework.internal.core.BundleContextImpl.start(BundleContextImpl.java:683)
at org.eclipse.osgi.framework.internal.core.BundleHost.startWorker(BundleHost.java:381)
at org.eclipse.osgi.framework.internal.core.AbstractBundle.start(AbstractBundle.java:299)
at org.eclipse.osgi.framework.util.SecureAction.start(SecureAction.java:440)
at org.eclipse.osgi.internal.loader.BundleLoader.setLazyTrigger(BundleLoader.java:268)
at org.eclipse.core.runtime.internal.adaptor.EclipseLazyStarter.postFindLocalClass(EclipseLazyStarter.java:107)
... 123 more
Caused by: org.eclipse.core.runtime.AssertionFailedException: null argument:
at org.eclipse.core.runtime.Assert.isNotNull(Assert.java:85)
at org.eclipse.core.runtime.Assert.isNotNull(Assert.java:73)
at org.eclipse.core.internal.events.ResourceChangeListenerList.add(ResourceChangeListenerList.java:67)
at org.eclipse.core.internal.events.NotificationManager.addListener(NotificationManager.java:108)
at org.eclipse.core.internal.resources.Workspace.addResourceChangeListener(Workspace.java:334)
at org.eclipselabs.spray.xtext.ui.internal.SprayActivatorExt.start(SprayActivatorExt.java:31)
at org.eclipse.osgi.framework.internal.core.BundleContextImpl$1.run(BundleContextImpl.java:711)
at java.security.AccessController.doPrivileged(Native Method)
at org.eclipse.osgi.framework.internal.core.BundleContextImpl.startActivator(BundleContextImpl.java:702)
... 129 more
276025 [Worker-8] ERROR org.eclipse.xtext.internal.ResourceServiceProviderDescriptor - Plug-in org.eclipselabs.spray.xtext.ui was unable to load class org.eclipselabs.spray.xtext.ui.SprayExecutableExtensionFactory.
org.eclipse.core.runtime.CoreException: Plug-in org.eclipselabs.spray.xtext.ui was unable to load class org.eclipselabs.spray.xtext.ui.SprayExecutableExtensionFactory.
at org.eclipse.core.internal.registry.osgi.RegistryStrategyOSGI.throwException(RegistryStrategyOSGI.java:194)
at org.eclipse.core.internal.registry.osgi.RegistryStrategyOSGI.createExecutableExtension(RegistryStrategyOSGI.java:176)
at org.eclipse.core.internal.registry.ExtensionRegistry.createExecutableExtension(ExtensionRegistry.java:905)
at org.eclipse.core.internal.registry.ConfigurationElement.createExecutableExtension(ConfigurationElement.java:243)
at org.eclipse.core.internal.registry.ConfigurationElementHandle.createExecutableExtension(ConfigurationElementHandle.java:55)
at org.eclipse.xtext.internal.ResourceServiceProviderDescriptor.get(ResourceServiceProviderDescriptor.java:40)
at org.eclipse.xtext.internal.ResourceServiceProviderDescriptor.get(ResourceServiceProviderDescriptor.java:1)
at org.eclipse.xtext.resource.impl.ResourceServiceProviderRegistryImpl$InternalData.getServiceProvider(ResourceServiceProviderRegistryImpl.java:40)
at org.eclipse.xtext.resource.impl.ResourceServiceProviderRegistryImpl.getResourceServiceProvider(ResourceServiceProviderRegistryImpl.java:75)
at org.eclipse.xtext.resource.impl.ResourceServiceProviderRegistryImpl.getResourceServiceProvider(ResourceServiceProviderRegistryImpl.java:91)
at org.eclipse.xtext.ui.resource.UriValidator.isValid(UriValidator.java:27)
at org.eclipse.xtext.ui.resource.Storage2UriMapperImpl.isValidUri(Storage2UriMapperImpl.java:99)
at org.eclipse.xtext.ui.resource.Storage2UriMapperImpl.getUri(Storage2UriMapperImpl.java:83)
at org.eclipse.xtext.ui.containers.AbstractStorage2UriMapperClient.getUri(AbstractStorage2UriMapperClient.java:27)
at org.eclipse.xtext.ui.containers.WorkspaceProjectsStateHelper$1.visit(WorkspaceProjectsStateHelper.java:66)
at org.eclipse.core.internal.resources.Resource$2.visit(Resource.java:106)
at org.eclipse.core.internal.resources.Resource$1.visitElement(Resource.java:65)
at org.eclipse.core.internal.watson.ElementTreeIterator.doIteration(ElementTreeIterator.java:82)
at org.eclipse.core.internal.watson.ElementTreeIterator.doIteration(ElementTreeIterator.java:86)
at org.eclipse.core.internal.watson.ElementTreeIterator.doIteration(ElementTreeIterator.java:86)
at org.eclipse.core.internal.watson.ElementTreeIterator.iterate(ElementTreeIterator.java:127)
at org.eclipse.core.internal.resources.Resource.accept(Resource.java:75)
at org.eclipse.core.internal.resources.Resource.accept(Resource.java:104)
at org.eclipse.core.internal.resources.Resource.accept(Resource.java:88)
at org.eclipse.xtext.ui.containers.WorkspaceProjectsStateHelper.initContainedURIs(WorkspaceProjectsStateHelper.java:63)
at org.eclipse.xtext.ui.containers.JavaProjectsState.doInitContainedURIs(JavaProjectsState.java:35)
at org.eclipse.xtext.ui.containers.AbstractAllContainersState.initContainedURIs(AbstractAllContainersState.java:147)
at org.eclipse.xtext.ui.containers.AbstractAllContainersState.isEmpty(AbstractAllContainersState.java:143)
at org.eclipse.xtext.resource.containers.ContainerState.isEmpty(ContainerState.java:32)
at org.eclipse.xtext.resource.containers.StateBasedContainer.isEmpty(StateBasedContainer.java:72)
at org.eclipse.xtext.resource.containers.StateBasedContainerManager.getVisibleContainers(StateBasedContainerManager.java:82)
at org.eclipse.xtext.resource.containers.StateBasedContainerManager.getVisibleContainers(StateBasedContainerManager.java:55)
at org.eclipse.xtext.scoping.impl.DefaultGlobalScopeProvider.getVisibleContainers(DefaultGlobalScopeProvider.java:72)
at org.eclipse.xtext.scoping.impl.DefaultGlobalScopeProvider.getScope(DefaultGlobalScopeProvider.java:49)
at org.eclipse.xtext.scoping.impl.DefaultGlobalScopeProvider.getScope(DefaultGlobalScopeProvider.java:61)
at org.eclipse.xtext.scoping.impl.AbstractGlobalScopeProvider.getScope(AbstractGlobalScopeProvider.java:48)
at org.eclipse.xtext.common.types.xtext.TypesAwareDefaultGlobalScopeProvider.getScope(TypesAwareDefaultGlobalScopeProvider.java:41)
at org.eclipse.xtext.scoping.impl.AbstractGlobalScopeDelegatingScopeProvider.getGlobalScope(AbstractGlobalScopeDelegatingScopeProvider.java:46)
at org.eclipse.xtext.scoping.impl.AbstractGlobalScopeDelegatingScopeProvider.getGlobalScope(AbstractGlobalScopeDelegatingScopeProvider.java:42)
at org.eclipse.xtext.scoping.impl.ImportedNamespaceAwareLocalScopeProvider.getResourceScope(ImportedNamespaceAwareLocalScopeProvider.java:96)
at org.eclipse.xtext.scoping.impl.ImportedNamespaceAwareLocalScopeProvider.getScope(ImportedNamespaceAwareLocalScopeProvider.java:89)
at org.eclipse.xtext.scoping.impl.ImportedNamespaceAwareLocalScopeProvider.getScope(ImportedNamespaceAwareLocalScopeProvider.java:87)
at org.eclipse.xtext.scoping.impl.ImportedNamespaceAwareLocalScopeProvider.getScope(ImportedNamespaceAwareLocalScopeProvider.java:87)
at org.eclipse.xtext.scoping.impl.ImportedNamespaceAwareLocalScopeProvider.getScope(ImportedNamespaceAwareLocalScopeProvider.java:87)
at org.eclipse.xtext.scoping.impl.AbstractDeclarativeScopeProvider.delegateGetScope(AbstractDeclarativeScopeProvider.java:72)
at org.eclipse.xtext.scoping.impl.AbstractDeclarativeScopeProvider.getScope(AbstractDeclarativeScopeProvider.java:102)
at org.eclipse.xtext.linking.impl.DefaultLinkingService.getScope(DefaultLinkingService.java:59)
at org.eclipse.xtext.linking.impl.DefaultLinkingService.getLinkedObjects(DefaultLinkingService.java:119)
at org.eclipse.xtext.linking.lazy.LazyLinkingResource.getEObject(LazyLinkingResource.java:175)
at org.eclipse.xtext.linking.lazy.LazyLinkingResource.resolveLazyCrossReference(LazyLinkingResource.java:143)
at org.eclipse.xtext.linking.lazy.LazyLinkingResource.resolveLazyCrossReferences(LazyLinkingResource.java:104)
at org.eclipse.xtext.EcoreUtil2.resolveLazyCrossReferences(EcoreUtil2.java:491)
at org.eclipse.xtext.builder.clustering.ClusteringBuilderState.doUpdate(ClusteringBuilderState.java:210)
at org.eclipse.xtext.builder.builderState.AbstractBuilderState.update(AbstractBuilderState.java:107)
at org.eclipse.xtext.builder.impl.XtextBuilder.doBuild(XtextBuilder.java:158)
at org.eclipse.xtext.builder.impl.XtextBuilder.fullBuild(XtextBuilder.java:183)
at org.eclipse.xtext.builder.impl.XtextBuilder.build(XtextBuilder.java:85)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:321)
at org.eclipse.core.internal.events.BuildManager.build(BuildManager.java:396)
at org.eclipse.core.internal.resources.Project$1.run(Project.java:618)
at org.eclipse.core.internal.resources.Workspace.run(Workspace.java:2344)
at org.eclipse.core.internal.resources.Project.internalBuild(Project.java:597)
at org.eclipse.core.internal.resources.Project.build(Project.java:124)
at org.eclipse.xtext.builder.impl.BuildScheduler$BuildJob.run(BuildScheduler.java:163)
at org.eclipse.core.internal.jobs.Worker.run(Worker.java:54)
Caused by: org.eclipse.core.runtime.internal.adaptor.EclipseLazyStarter$TerminatingClassNotFoundException: An error occurred while automatically activating bundle org.eclipselabs.spray.xtext.ui (912).
at org.eclipse.core.runtime.internal.adaptor.EclipseLazyStarter.postFindLocalClass(EclipseLazyStarter.java:122)
at org.eclipse.osgi.baseadaptor.loader.ClasspathManager.findLocalClass(ClasspathManager.java:462)
at org.eclipse.osgi.internal.baseadaptor.DefaultClassLoader.findLocalClass(DefaultClassLoader.java:216)
at org.eclipse.osgi.internal.loader.BundleLoader.findLocalClass(BundleLoader.java:400)
at org.eclipse.osgi.internal.loader.BundleLoader.findClassInternal(BundleLoader.java:476)
at org.eclipse.osgi.internal.loader.BundleLoader.findClass(BundleLoader.java:429)
at org.eclipse.osgi.internal.loader.BundleLoader.findClass(BundleLoader.java:417)
at org.eclipse.osgi.internal.baseadaptor.DefaultClassLoader.loadClass(DefaultClassLoader.java:107)
at java.lang.ClassLoader.loadClass(ClassLoader.java:247)
at org.eclipse.osgi.internal.loader.BundleLoader.loadClass(BundleLoader.java:345)
at org.eclipse.osgi.framework.internal.core.BundleHost.loadClass(BundleHost.java:229)
at org.eclipse.osgi.framework.internal.core.AbstractBundle.loadClass(AbstractBundle.java:1207)
at org.eclipse.core.internal.registry.osgi.RegistryStrategyOSGI.createExecutableExtension(RegistryStrategyOSGI.java:174)
at org.eclipse.core.internal.registry.ExtensionRegistry.createExecutableExtension(ExtensionRegistry.java:905)
at org.eclipse.core.internal.registry.ConfigurationElement.createExecutableExtension(ConfigurationElement.java:243)
at org.eclipse.core.internal.registry.ConfigurationElementHandle.createExecutableExtension(ConfigurationElementHandle.java:55)
at org.eclipse.xtext.internal.ResourceServiceProviderDescriptor.get(ResourceServiceProviderDescriptor.java:40)
at org.eclipse.xtext.internal.ResourceServiceProviderDescriptor.get(ResourceServiceProviderDescriptor.java:1)
at org.eclipse.xtext.resource.impl.ResourceServiceProviderRegistryImpl$InternalData.getServiceProvider(ResourceServiceProviderRegistryImpl.java:40)
at org.eclipse.xtext.resource.impl.ResourceServiceProviderRegistryImpl.getResourceServiceProvider(ResourceServiceProviderRegistryImpl.java:75)
at org.eclipse.xtext.resource.impl.ResourceServiceProviderRegistryImpl.getResourceServiceProvider(ResourceServiceProviderRegistryImpl.java:91)
at org.eclipse.xtext.ui.resource.UriValidator.isValid(UriValidator.java:27)
at org.eclipse.xtext.ui.resource.Storage2UriMapperImpl.isValidUri(Storage2UriMapperImpl.java:99)
at org.eclipse.xtext.ui.resource.Storage2UriMapperImpl.getUri(Storage2UriMapperImpl.java:83)
at org.eclipse.xtext.ui.containers.AbstractStorage2UriMapperClient.getUri(AbstractStorage2UriMapperClient.java:27)
at org.eclipse.xtext.ui.containers.JavaProjectsStateHelper$2.visit(JavaProjectsStateHelper.java:107)
at org.eclipse.core.internal.resources.Resource$2.visit(Resource.java:106)
at org.eclipse.core.internal.resources.Resource$1.visitElement(Resource.java:65)
at org.eclipse.core.internal.watson.ElementTreeIterator.doIteration(ElementTreeIterator.java:82)
at org.eclipse.core.internal.watson.ElementTreeIterator.doIteration(ElementTreeIterator.java:86)
at org.eclipse.core.internal.watson.ElementTreeIterator.iterate(ElementTreeIterator.java:127)
at org.eclipse.core.internal.resources.Resource.accept(Resource.java:75)
at org.eclipse.core.internal.resources.Resource.accept(Resource.java:104)
at org.eclipse.core.internal.resources.Resource.accept(Resource.java:88)
at org.eclipse.xtext.ui.containers.JavaProjectsStateHelper.initContainedURIs(JavaProjectsStateHelper.java:104)
at org.eclipse.xtext.ui.containers.JavaProjectsState.doInitContainedURIs(JavaProjectsState.java:32)
at org.eclipse.xtext.ui.containers.AbstractAllContainersState.initContainedURIs(AbstractAllContainersState.java:147)
at org.eclipse.xtext.ui.containers.AbstractAllContainersState.isEmpty(AbstractAllContainersState.java:143)
at org.eclipse.xtext.resource.containers.ContainerState.isEmpty(ContainerState.java:32)
at org.eclipse.xtext.resource.containers.StateBasedContainer.isEmpty(StateBasedContainer.java:72)
at org.eclipse.xtext.resource.containers.StateBasedContainerManager.getVisibleContainers(StateBasedContainerManager.java:82)
at org.eclipse.xtext.resource.containers.StateBasedContainerManager.getVisibleContainers(StateBasedContainerManager.java:55)
at org.eclipse.xtext.scoping.impl.DefaultGlobalScopeProvider.getVisibleContainers(DefaultGlobalScopeProvider.java:72)
at org.eclipse.xtext.scoping.impl.DefaultGlobalScopeProvider.getScope(DefaultGlobalScopeProvider.java:49)
at org.eclipse.xtext.scoping.impl.DefaultGlobalScopeProvider.getScope(DefaultGlobalScopeProvider.java:61)
at org.eclipse.xtext.scoping.impl.AbstractGlobalScopeProvider.getScope(AbstractGlobalScopeProvider.java:48)
at org.eclipse.xtext.common.types.xtext.TypesAwareDefaultGlobalScopeProvider.getScope(TypesAwareDefaultGlobalScopeProvider.java:41)
at org.eclipse.xtext.scoping.impl.AbstractGlobalScopeDelegatingScopeProvider.getGlobalScope(AbstractGlobalScopeDelegatingScopeProvider.java:46)
at org.eclipse.xtext.scoping.impl.AbstractGlobalScopeDelegatingScopeProvider.getGlobalScope(AbstractGlobalScopeDelegatingScopeProvider.java:42)
at org.eclipse.xtext.scoping.impl.ImportedNamespaceAwareLocalScopeProvider.getResourceScope(ImportedNamespaceAwareLocalScopeProvider.java:96)
at org.eclipse.xtext.scoping.impl.ImportedNamespaceAwareLocalScopeProvider.getScope(ImportedNamespaceAwareLocalScopeProvider.java:89)
at org.eclipse.xtext.scoping.impl.ImportedNamespaceAwareLocalScopeProvider.getScope(ImportedNamespaceAwareLocalScopeProvider.java:87)
at org.eclipse.xtext.scoping.impl.ImportedNamespaceAwareLocalScopeProvider.getScope(ImportedNamespaceAwareLocalScopeProvider.java:87)
at org.eclipse.xtext.scoping.impl.ImportedNamespaceAwareLocalScopeProvider.getScope(ImportedNamespaceAwareLocalScopeProvider.java:87)
at org.eclipse.xtext.scoping.impl.AbstractDeclarativeScopeProvider.delegateGetScope(AbstractDeclarativeScopeProvider.java:72)
at org.eclipse.xtext.scoping.impl.AbstractDeclarativeScopeProvider.getScope(AbstractDeclarativeScopeProvider.java:102)
at org.eclipse.xtext.linking.impl.DefaultLinkingService.getScope(DefaultLinkingService.java:59)
at org.eclipse.xtext.linking.impl.DefaultLinkingService.getLinkedObjects(DefaultLinkingService.java:119)
at org.eclipse.xtext.linking.lazy.LazyLinkingResource.getEObject(LazyLinkingResource.java:175)
at org.eclipse.emf.ecore.resource.impl.ResourceSetImpl.getEObject(ResourceSetImpl.java:219)
at org.eclipse.emf.ecore.util.EcoreUtil.resolve(EcoreUtil.java:203)
at org.eclipse.emf.ecore.util.EcoreUtil.resolve(EcoreUtil.java:263)
at org.eclipse.emf.ecore.impl.BasicEObjectImpl.eResolveProxy(BasicEObjectImpl.java:1483)
at org.eclipse.emf.mwe2.language.mwe2.impl.ComponentImpl.getModule(ComponentImpl.java:116)
at org.eclipse.emf.mwe2.language.resource.MweLocationInFileProvider.getIdentifierFeature(MweLocationInFileProvider.java:43)
at org.eclipse.xtext.resource.DefaultLocationInFileProvider.getLocationNodes(DefaultLocationInFileProvider.java:130)
at org.eclipse.xtext.resource.DefaultLocationInFileProvider.getTextRegion(DefaultLocationInFileProvider.java:54)
at org.eclipse.xtext.resource.DefaultLocationInFileProvider.getSignificantTextRegion(DefaultLocationInFileProvider.java:38)
at org.eclipse.xtext.ui.editor.folding.DefaultFoldingRegionProvider.computeObjectFolding(DefaultFoldingRegionProvider.java:103)
at org.eclipse.xtext.ui.editor.folding.DefaultFoldingRegionProvider.computeObjectFolding(DefaultFoldingRegionProvider.java:86)
at org.eclipse.xtext.ui.editor.folding.DefaultFoldingRegionProvider.doGetFoldingRegions(DefaultFoldingRegionProvider.java:68)
at org.eclipse.xtext.ui.editor.folding.DefaultFoldingRegionProvider$1.exec(DefaultFoldingRegionProvider.java:60)
at org.eclipse.xtext.ui.editor.folding.DefaultFoldingRegionProvider$1.exec(DefaultFoldingRegionProvider.java:1)
at org.eclipse.xtext.util.concurrent.AbstractReadWriteAcces.readOnly(AbstractReadWriteAcces.java:32)
at org.eclipse.xtext.ui.editor.model.XtextDocument.readOnly(XtextDocument.java:78)
at org.eclipse.xtext.ui.editor.folding.DefaultFoldingRegionProvider.getFoldingRegions(DefaultFoldingRegionProvider.java:56)
at org.eclipse.xtext.ui.editor.folding.DefaultFoldingStructureProvider.calculateProjectionAnnotationModel(DefaultFoldingStructureProvider.java:114)
at org.eclipse.xtext.ui.editor.folding.DefaultFoldingStructureProvider.initialize(DefaultFoldingStructureProvider.java:58)
at org.eclipse.xtext.ui.editor.folding.DefaultFoldingStructureProvider.handleProjectionEnabled(DefaultFoldingStructureProvider.java:99)
at org.eclipse.xtext.ui.editor.folding.DefaultFoldingStructureProvider$ProjectionChangeListener.projectionEnabled(DefaultFoldingStructureProvider.java:186)
at org.eclipse.jface.text.source.projection.ProjectionViewer.fireProjectionEnabled(ProjectionViewer.java:489)
at org.eclipse.jface.text.source.projection.ProjectionViewer.enableProjection(ProjectionViewer.java:537)
at org.eclipse.jface.text.source.projection.ProjectionViewer.doOperation(ProjectionViewer.java:1441)
at org.eclipse.xtext.ui.editor.XtextEditor.installFoldingSupport(XtextEditor.java:471)
at org.eclipse.xtext.ui.editor.XtextEditor.createPartControl(XtextEditor.java:453)
at org.eclipse.ui.internal.EditorReference.createPartHelper(EditorReference.java:670)
at org.eclipse.ui.internal.EditorReference.createPart(EditorReference.java:465)
at org.eclipse.ui.internal.WorkbenchPartReference.getPart(WorkbenchPartReference.java:595)
at org.eclipse.ui.internal.EditorAreaHelper.setVisibleEditor(EditorAreaHelper.java:271)
at org.eclipse.ui.internal.EditorManager.setVisibleEditor(EditorManager.java:1459)
at org.eclipse.ui.internal.EditorManager$5.runWithException(EditorManager.java:972)
at org.eclipse.ui.internal.StartupThreading$StartupRunnable.run(StartupThreading.java:31)
at org.eclipse.swt.widgets.RunnableLock.run(RunnableLock.java:35)
at org.eclipse.swt.widgets.Synchronizer.runAsyncMessages(Synchronizer.java:135)
at org.eclipse.swt.widgets.Display.runAsyncMessages(Display.java:4140)
at org.eclipse.swt.widgets.Display.readAndDispatch(Display.java:3757)
at org.eclipse.ui.application.WorkbenchAdvisor.openWindows(WorkbenchAdvisor.java:803)
at org.eclipse.ui.internal.Workbench$33.runWithException(Workbench.java:1595)
at org.eclipse.ui.internal.StartupThreading$StartupRunnable.run(StartupThreading.java:31)
at org.eclipse.swt.widgets.Synchronizer.syncExec(Synchronizer.java:180)
at org.eclipse.ui.internal.UISynchronizer.syncExec(UISynchronizer.java:150)
at org.eclipse.swt.widgets.Display.syncExec(Display.java:4683)
at org.eclipse.ui.internal.StartupThreading.runWithoutExceptions(StartupThreading.java:94)
at org.eclipse.ui.internal.Workbench.init(Workbench.java:1590)
at org.eclipse.ui.internal.Workbench.runUI(Workbench.java:2623)
at org.eclipse.ui.internal.Workbench.access$4(Workbench.java:2494)
at org.eclipse.ui.internal.Workbench$7.run(Workbench.java:674)
at org.eclipse.core.databinding.observable.Realm.runWithDefault(Realm.java:332)
at org.eclipse.ui.internal.Workbench.createAndRunWorkbench(Workbench.java:667)
at org.eclipse.ui.PlatformUI.createAndRunWorkbench(PlatformUI.java:149)
at org.eclipse.ui.internal.ide.application.IDEApplication.start(IDEApplication.java:123)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:344)
at org.eclipse.core.runtime.adaptor.EclipseStarter.run(EclipseStarter.java:179)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.eclipse.equinox.launcher.Main.invokeFramework(Main.java:622)
at org.eclipse.equinox.launcher.Main.basicRun(Main.java:577)
at org.eclipse.equinox.launcher.Main.run(Main.java:1410)
at org.eclipse.equinox.launcher.Main.main(Main.java:1386)
Caused by: org.osgi.framework.BundleException: Exception in org.eclipselabs.spray.xtext.ui.internal.SprayActivatorExt.start() of bundle org.eclipselabs.spray.xtext.ui.
at org.eclipse.osgi.framework.internal.core.BundleContextImpl.startActivator(BundleContextImpl.java:734)
at org.eclipse.osgi.framework.internal.core.BundleContextImpl.start(BundleContextImpl.java:683)
at org.eclipse.osgi.framework.internal.core.BundleHost.startWorker(BundleHost.java:381)
at org.eclipse.osgi.framework.internal.core.AbstractBundle.start(AbstractBundle.java:299)
at org.eclipse.osgi.framework.util.SecureAction.start(SecureAction.java:440)
at org.eclipse.osgi.internal.loader.BundleLoader.setLazyTrigger(BundleLoader.java:268)
at org.eclipse.core.runtime.internal.adaptor.EclipseLazyStarter.postFindLocalClass(EclipseLazyStarter.java:107)
... 123 more
Caused by: org.eclipse.core.runtime.AssertionFailedException: null argument:
at org.eclipse.core.runtime.Assert.isNotNull(Assert.java:85)
at org.eclipse.core.runtime.Assert.isNotNull(Assert.java:73)
at org.eclipse.core.internal.events.ResourceChangeListenerList.add(ResourceChangeListenerList.java:67)
at org.eclipse.core.internal.events.NotificationManager.addListener(NotificationManager.java:108)
at org.eclipse.core.internal.resources.Workspace.addResourceChangeListener(Workspace.java:334)
at org.eclipselabs.spray.xtext.ui.internal.SprayActivatorExt.start(SprayActivatorExt.java:31)
at org.eclipse.osgi.framework.internal.core.BundleContextImpl$1.run(BundleContextImpl.java:711)
at java.security.AccessController.doPrivileged(Native Method)
at org.eclipse.osgi.framework.internal.core.BundleContextImpl.startActivator(BundleContextImpl.java:702)
... 129 more
12.12.2011 23:58:57 (karsten.thoms): This issue was closed by revision 79f687aa50df.
- stakeholder: Spray user
- keywords: Type: Defect, Priority: Medium
- status: DONE

## issue0098
Content propsoal in Style DSL Editor causes exception
11.12.2011 11:33:02 (de.abg.reichert.joerg):
!ENTRY org.eclipse.ui 4 4 2011-12-11 10:42:53.299
!MESSAGE &quot;Content Assist&quot; did not complete normally. Please see the log for more information.
!ENTRY org.eclipse.ui 4 0 2011-12-11 10:42:53.299
!MESSAGE java.lang.reflect.InvocationTargetException
!STACK 0
java.lang.RuntimeException: java.lang.reflect.InvocationTargetException
at org.eclipse.xtext.ui.editor.contentassist.antlr.AbstractContentAssistParser.getFollowElements(AbstractContentAssistParser.java:237)
at org.eclipse.xtext.ui.editor.contentassist.antlr.AbstractContentAssistParser.getFollowElements(AbstractContentAssistParser.java:141)
at org.eclipse.xtext.ui.editor.contentassist.antlr.ParserBasedContentAssistContextFactory$StatefulFactory.computeFollowElements(ParserBasedContentAssistContextFactory.java:387)
at org.eclipse.xtext.ui.editor.contentassist.antlr.ParserBasedContentAssistContextFactory$StatefulFactory.computeFollowElements(ParserBasedContentAssistContextFactory.java:343)
at org.eclipse.xtext.ui.editor.contentassist.antlr.ParserBasedContentAssistContextFactory$StatefulFactory.computeFollowElements(ParserBasedContentAssistContextFactory.java:337)
at org.eclipse.xtext.ui.editor.contentassist.antlr.ParserBasedContentAssistContextFactory$StatefulFactory.doCreateContexts(ParserBasedContentAssistContextFactory.java:286)
at org.eclipse.xtext.ui.editor.contentassist.antlr.ParserBasedContentAssistContextFactory$StatefulFactory.handleLastCompleteNodeIsAtEndOfDatatypeNode(ParserBasedContentAssistContextFactory.java:212)
at org.eclipse.xtext.ui.editor.contentassist.antlr.ParserBasedContentAssistContextFactory$StatefulFactory.doCreateContexts(ParserBasedContentAssistContextFactory.java:161)
at org.eclipse.xtext.ui.editor.contentassist.antlr.ParserBasedContentAssistContextFactory$StatefulFactory.create(ParserBasedContentAssistContextFactory.java:148)
at org.eclipse.xtext.ui.editor.contentassist.antlr.ParserBasedContentAssistContextFactory.create(ParserBasedContentAssistContextFactory.java:549)
at org.eclipse.xtext.ui.editor.contentassist.CompletionProposalComputer.exec(CompletionProposalComputer.java:48)
at org.eclipse.xtext.ui.editor.contentassist.CompletionProposalComputer.exec(CompletionProposalComputer.java:1)
at org.eclipse.xtext.util.concurrent.AbstractReadWriteAcces.readOnly(AbstractReadWriteAcces.java:32)
at org.eclipse.xtext.ui.editor.model.XtextDocument.readOnly(XtextDocument.java:78)
at org.eclipse.xtext.ui.editor.contentassist.XtextContentAssistProcessor.computeCompletionProposals(XtextContentAssistProcessor.java:69)
at org.eclipse.xtext.ui.editor.contentassist.RepeatedContentAssistProcessor.computeCompletionProposals(RepeatedContentAssistProcessor.java:73)
at org.eclipse.jface.text.contentassist.ContentAssistant.computeCompletionProposals(ContentAssistant.java:1830)
at org.eclipse.jface.text.contentassist.CompletionProposalPopup.computeProposals(CompletionProposalPopup.java:556)
at org.eclipse.jface.text.contentassist.CompletionProposalPopup.access$16(CompletionProposalPopup.java:553)
at org.eclipse.jface.text.contentassist.CompletionProposalPopup$2.run(CompletionProposalPopup.java:488)
at org.eclipse.swt.custom.BusyIndicator.showWhile(BusyIndicator.java:70)
at org.eclipse.jface.text.contentassist.CompletionProposalPopup.showProposals(CompletionProposalPopup.java:482)
at org.eclipse.jface.text.contentassist.ContentAssistant.showPossibleCompletions(ContentAssistant.java:1656)
at org.eclipse.jface.text.source.SourceViewer.doOperation(SourceViewer.java:930)
at org.eclipse.jface.text.source.projection.ProjectionViewer.doOperation(ProjectionViewer.java:1534)
at org.eclipse.ui.texteditor.ContentAssistAction$1.run(ContentAssistAction.java:82)
at org.eclipse.swt.custom.BusyIndicator.showWhile(BusyIndicator.java:70)
at org.eclipse.ui.texteditor.ContentAssistAction.run(ContentAssistAction.java:80)
at org.eclipse.jface.action.Action.runWithEvent(Action.java:498)
at org.eclipse.ui.commands.ActionHandler.execute(ActionHandler.java:185)
at org.eclipse.ui.internal.handlers.LegacyHandlerWrapper.execute(LegacyHandlerWrapper.java:109)
at org.eclipse.core.commands.Command.executeWithChecks(Command.java:476)
at org.eclipse.core.commands.ParameterizedCommand.executeWithChecks(ParameterizedCommand.java:508)
at org.eclipse.ui.internal.handlers.HandlerService.executeCommand(HandlerService.java:169)
at org.eclipse.ui.internal.keys.WorkbenchKeyboard.executeCommand(WorkbenchKeyboard.java:468)
at org.eclipse.ui.internal.keys.WorkbenchKeyboard.press(WorkbenchKeyboard.java:786)
at org.eclipse.ui.internal.keys.WorkbenchKeyboard.processKeyEvent(WorkbenchKeyboard.java:885)
at org.eclipse.ui.internal.keys.WorkbenchKeyboard.filterKeySequenceBindings(WorkbenchKeyboard.java:567)
at org.eclipse.ui.internal.keys.WorkbenchKeyboard.access$3(WorkbenchKeyboard.java:508)
at org.eclipse.ui.internal.keys.WorkbenchKeyboard$KeyDownFilter.handleEvent(WorkbenchKeyboard.java:123)
at org.eclipse.swt.widgets.EventTable.sendEvent(EventTable.java:84)
at org.eclipse.swt.widgets.Display.filterEvent(Display.java:1262)
at org.eclipse.swt.widgets.Widget.sendEvent(Widget.java:1052)
at org.eclipse.swt.widgets.Widget.sendEvent(Widget.java:1077)
at org.eclipse.swt.widgets.Widget.sendEvent(Widget.java:1062)
at org.eclipse.swt.widgets.Widget.sendKeyEvent(Widget.java:1104)
at org.eclipse.swt.widgets.Widget.sendKeyEvent(Widget.java:1100)
at org.eclipse.swt.widgets.Widget.wmChar(Widget.java:1509)
at org.eclipse.swt.widgets.Control.WM_CHAR(Control.java:4640)
at org.eclipse.swt.widgets.Canvas.WM_CHAR(Canvas.java:345)
at org.eclipse.swt.widgets.Control.windowProc(Control.java:4528)
at org.eclipse.swt.widgets.Canvas.windowProc(Canvas.java:341)
at org.eclipse.swt.widgets.Display.windowProc(Display.java:4972)
at org.eclipse.swt.internal.win32.OS.DispatchMessageW(Native Method)
at org.eclipse.swt.internal.win32.OS.DispatchMessage(OS.java:2531)
at org.eclipse.swt.widgets.Display.readAndDispatch(Display.java:3752)
at org.eclipse.ui.internal.Workbench.runEventLoop(Workbench.java:2696)
at org.eclipse.ui.internal.Workbench.runUI(Workbench.java:2660)
at org.eclipse.ui.internal.Workbench.access$4(Workbench.java:2494)
at org.eclipse.ui.internal.Workbench$7.run(Workbench.java:674)
at org.eclipse.core.databinding.observable.Realm.runWithDefault(Realm.java:332)
at org.eclipse.ui.internal.Workbench.createAndRunWorkbench(Workbench.java:667)
at org.eclipse.ui.PlatformUI.createAndRunWorkbench(PlatformUI.java:149)
at org.eclipse.ui.internal.ide.application.IDEApplication.start(IDEApplication.java:123)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:344)
at org.eclipse.core.runtime.adaptor.EclipseStarter.run(EclipseStarter.java:179)
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.eclipse.equinox.launcher.Main.invokeFramework(Main.java:622)
at org.eclipse.equinox.launcher.Main.basicRun(Main.java:577)
at org.eclipse.equinox.launcher.Main.run(Main.java:1410)
at org.eclipse.equinox.launcher.Main.main(Main.java:1386)
Caused by: java.lang.reflect.InvocationTargetException
at sun.reflect.NativeMethodAccessorImpl.invoke0(Native Method)
at sun.reflect.NativeMethodAccessorImpl.invoke(NativeMethodAccessorImpl.java:39)
at sun.reflect.DelegatingMethodAccessorImpl.invoke(DelegatingMethodAccessorImpl.java:25)
at java.lang.reflect.Method.invoke(Method.java:597)
at org.eclipse.xtext.ui.editor.contentassist.antlr.AbstractContentAssistParser.getFollowElements(AbstractContentAssistParser.java:210)
... 76 more
Caused by: java.lang.IllegalStateException
at org.eclipse.xtext.parser.antlr.UnorderedGroupHelper$State.canLeave(UnorderedGroupHelper.java:228)
at org.eclipse.xtext.parser.antlr.UnorderedGroupHelper.canLeave(UnorderedGroupHelper.java:146)
at org.eclipse.xtext.ui.editor.contentassist.antlr.AbstractContentAssistParser$2.canLeave(AbstractContentAssistParser.java:132)
at org.eclipse.xtext.ui.editor.contentassist.antlr.AbstractContentAssistParser$3.announceEof(AbstractContentAssistParser.java:170)
at org.eclipse.xtext.ui.editor.contentassist.antlr.ObservableXtextTokenStream.LA(ObservableXtextTokenStream.java:48)
at org.antlr.runtime.DFA.predict(DFA.java:97)
at org.eclipse.xtext.ui.editor.contentassist.antlr.internal.DFA.predict(DFA.java:25)
at org.eclipselabs.spray.styles.ui.contentassist.antlr.internal.InternalStyleParser.rule__Line__UnorderedGroup_1__0(InternalStyleParser.java:43753)
at org.eclipselabs.spray.styles.ui.contentassist.antlr.internal.InternalStyleParser.synpred145_InternalStyle_fragment(InternalStyleParser.java:51009)
at org.eclipselabs.spray.styles.ui.contentassist.antlr.internal.InternalStyleParser.synpred145_InternalStyle(InternalStyleParser.java:51764)
at org.eclipselabs.spray.styles.ui.contentassist.antlr.internal.InternalStyleParser.rule__Line__UnorderedGroup_1(InternalStyleParser.java:43481)
at org.eclipselabs.spray.styles.ui.contentassist.antlr.internal.InternalStyleParser.rule__Line__Group__1__Impl(InternalStyleParser.java:13480)
at org.eclipselabs.spray.styles.ui.contentassist.antlr.internal.InternalStyleParser.rule__Line__Group__1(InternalStyleParser.java:13438)
at org.eclipselabs.spray.styles.ui.contentassist.antlr.internal.InternalStyleParser.rule__Line__Group__0(InternalStyleParser.java:13364)
at org.eclipselabs.spray.styles.ui.contentassist.antlr.internal.InternalStyleParser.ruleLine(InternalStyleParser.java:754)
at org.eclipselabs.spray.styles.ui.contentassist.antlr.internal.InternalStyleParser.rule__StyleLayout__LineAssignment_1_2(InternalStyleParser.java:44150)
at org.eclipselabs.spray.styles.ui.contentassist.antlr.internal.InternalStyleParser.synpred132_InternalStyle_fragment(InternalStyleParser.java:50674)
at org.eclipselabs.spray.styles.ui.contentassist.antlr.internal.InternalStyleParser.synpred132_InternalStyle(InternalStyleParser.java:51778)
at org.eclipselabs.spray.styles.ui.contentassist.antlr.internal.InternalStyleParser$DFA90.specialStateTransition(InternalStyleParser.java:54027)
at org.antlr.runtime.DFA.predict(DFA.java:80)
at org.eclipse.xtext.ui.editor.contentassist.antlr.internal.DFA.predict(DFA.java:25)
at org.eclipselabs.spray.styles.ui.contentassist.antlr.internal.InternalStyleParser.rule__StyleLayout__UnorderedGroup_1__Impl(InternalStyleParser.java:42249)
at org.eclipselabs.spray.styles.ui.contentassist.antlr.internal.InternalStyleParser.rule__StyleLayout__UnorderedGroup_1__0(InternalStyleParser.java:42473)
at org.eclipselabs.spray.styles.ui.contentassist.antlr.internal.InternalStyleParser.rule__StyleLayout__UnorderedGroup_1(InternalStyleParser.java:42207)
... 81 more
----
In the classpath are org.antlr.runtime_3.2.0.v201101311130.jar, org.antlr.generator_3.2.0.v201108011202.jar and de.itemis.xtext.antlr_2.0.0.v201108011202.jar
Also any other content assist do not work for me although it is implemented in /org.eclipselabs.spray.styles.ui/src/org/eclipselabs/spray/styles/ui/contentassist/StyleProposalProvider.java
11.12.2011 11:34:37 (de.abg.reichert.joerg):
11.12.2011 15:50:53 (fabio.filippelli): Reassigned to Michael
13.12.2011 20:31:07 (fabio.filippelli): Bug should be fixed with commits 5e4b1b053478 and 1a57cbf46943.
- stakeholder: Spray user
- keywords: Type: Defect, Priority: Medium, Styles-DSL
- status: DONE

## issue0099
Shape Generator runs on NPE
11.12.2011 11:33:48 (de.abg.reichert.joerg):
shape MyShape {
size-max (width=200, height=100)
ellipse
}
!ENTRY org.apache.log4j 4 0 2011-12-11 10:57:13.130
!MESSAGE org.eclipse.xtext.builder.impl.XtextBuilder -
!STACK 0
java.lang.NullPointerException
at org.eclipselabs.spray.shapes.generator.ShapeGenerator._createElement(ShapeGenerator.java:412)
at org.eclipselabs.spray.shapes.generator.ShapeGenerator.createElement(ShapeGenerator.java:504)
at org.eclipselabs.spray.shapes.generator.ShapeGenerator.body(ShapeGenerator.java:185)
at org.eclipselabs.spray.shapes.generator.ShapeGenerator.compile(ShapeGenerator.java:64)
at org.eclipselabs.spray.shapes.generator.ShapeGenerator.doGenerate(ShapeGenerator.java:41)
at org.eclipse.xtext.builder.BuilderParticipant.handleChangedContents(BuilderParticipant.java:222)
at org.eclipse.xtext.builder.BuilderParticipant.build(BuilderParticipant.java:168)
at org.eclipse.xtext.builder.impl.RegistryBuilderParticipant.build(RegistryBuilderParticipant.java:60)
at org.eclipse.xtext.builder.impl.XtextBuilder.doBuild(XtextBuilder.java:160)
at org.eclipse.xtext.builder.impl.XtextBuilder.incrementalBuild(XtextBuilder.java:141)
at org.eclipse.xtext.builder.impl.XtextBuilder.build(XtextBuilder.java:91)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:239)
at org.eclipse.core.internal.events.BuildManager$1.run(BuildManager.java:292)
at org.eclipse.core.runtime.SafeRunner.run(SafeRunner.java:42)
at org.eclipse.core.internal.events.BuildManager.basicBuild(BuildManager.java:295)
at org.eclipse.core.internal.events.BuildManager.basicBuildLoop(BuildManager.java:351)
at org.eclipse.core.internal.events.BuildManager.build(BuildManager.java:374)
at org.eclipse.core.internal.events.AutoBuildJob.doBuild(AutoBuildJob.java:143)
at org.eclipse.core.internal.events.AutoBuildJob.run(AutoBuildJob.java:241)
at org.eclipse.core.internal.jobs.Worker.run(Worker.java:54)
11.12.2011 11:34:15 (de.abg.reichert.joerg):
11.12.2011 11:34:51 (de.abg.reichert.joerg):
11.12.2011 12:48:40 (fabio.filippelli): quick fix by deactivating it - it is not yet finished and causes NPE
- stakeholder: Spray user
- keywords: Type: Defect, Priority: Medium, Shape-DSL
- status: DONE

## issue0100
Styles postprocessor classes must be compiled in separate module
14.12.2011 08:01:48 (karsten.thoms): The workflow of org.eclipselabs.spray.styles customizes the Xtext generator by the class StyleExtendedGenerator in the same plugin.
This workflow won't be executable in a Maven build, since the compiled class is required to execute the workflow before the class is actually compiled. The workflow is executed in the phase &quot;generate-sources&quot;, and the class StyleExtendedGenerator will be compiled in phase &quot;compile&quot;, which runs after the workflow.
This is a common scenario which only can be resolved by moving the classes a workflow requires into a seperate project, to which the using project has a dependency to. Then, Maven will compile the supporting classes before it builds the module that wants to use these classes.
I propose to introduce a plugin &quot;org.eclipse.spray.runtime.xtext&quot;, which will not only hold these postprocessors, but also other classes later that are Xtext specific additions. Ugly thing is that the postprocessor is logically dependent on the Styles DSL. Alternatively it could be a plugin named &quot;org.eclipselabs.spray.styles.workflow&quot; (or &quot;.xtext&quot;), which only holds the Xtext workflow customization.
The Styles specific plugins must be excluded from the build until this is solved.
14.12.2011 20:47:52 (fabio.filippelli): Added common workflow project with name "org.eclipse.spray.runtime.xtext" and referenced from style project.
19.12.2011 12:10:03 (de.abg.reichert.joerg): screenshot
19.12.2011 12:12:25 (fabio.filippelli): shapes are not yet integrated in spray due the development is not ready for integration.
The palette reference will be given from spray in later development.
24.03.2012 14:39:02 (fabio.filippelli):
- stakeholder: Spray user
- keywords: Type: Defect, Priority: High
- status: DONE

## issue0101
Compartment entry has no displayed name
19.12.2011 12:05:24 (de.abg.reichert.joerg): When generating the diagram editor for the model below the entry for the business class exists but display no name:
I also tried using the alias syntax but this does not fix the problem:
class BusinessClass alias business_class
import BusinessDomainDsl.*
diagram jos for BusinessDomainModel
class BusinessClass alias business_class :
container ( fill = dark_green ) {
text ( ) {
&quot;&lt;&lt;&quot; + eClass.name + &quot;&gt;&gt; &quot; + name
};
}
behavior {
// Enable create feature for this class and add it to the palette &quot;Shapes&quot;
create into types palette &quot;Shapes&quot;;
}
05.01.2012 15:57:35 (de.abg.reichert.joerg): fixed with dbdb97dc2c5aaaa4f91538526879a3df31c4153c
- stakeholder: Spray user
- keywords: Type: Defect, Priority: Medium
- status: DONE

## issue0102
Displayed shape name is incomplete
19.12.2011 12:13:17 (de.abg.reichert.joerg): Maybe this has the same cause as #101
From &quot;&lt;&lt;&quot; + eClass.name + &quot;&gt;&gt; &quot; + name
only &lt;&lt;BusinessClass&gt;&gt; is used, name is empty, although you see in the properties view, that it has been set.
import BusinessDomainDsl.*
diagram jos for BusinessDomainModel
class BusinessClass alias business_class :
container ( fill = dark_green ) {
text ( ) {
&quot;&lt;&lt;&quot; + eClass.name + &quot;&gt;&gt; &quot; + name
};
}
behavior {
// Enable create feature for this class and add it to the palette &quot;Shapes&quot;
create into types palette &quot;Shapes&quot;;
}
05.01.2012 15:58:29 (de.abg.reichert.joerg): as expected this error had the same reason as #101
- stakeholder: Spray user
- keywords: Type: Defect, Priority: Medium
- status: DONE

## issue0103
Shapes are not movable anymore
19.12.2011 12:15:22 (de.abg.reichert.joerg): Maybe by the introduction of the layout feature, when a shape has been once created in the diagram editor space it is not movable anymore. This was possible in an earlier Spray version.
05.01.2012 16:11:35 (de.abg.reichert.joerg): fixed with a0a0e961e9ef37543a40c05c1863d719fbcd311a
- stakeholder: Spray user
- keywords: Type: Defect, Priority: Medium
- status: DONE

## issue0104
Metamodel import from developer workspace in DSL not resolvable
19.12.2011 12:19:47 (de.abg.reichert.joerg): When using the Spray DSL editor from a runtime workspace and importing a meta model from the developer workspace (dependency set and resolvable in the MANIFEST file) the DSL editor cannot resolve and auto complete elements from this meta model. If you copy the meta model project in the runtime workspace, it works. There once has been issue that the other way did not work, now this case do not work anymore.
15.04.2012 23:13:24 (de.abg.reichert.joerg): this issue should be solved with issue #127
- stakeholder: Spray user
- keywords: Type: Defect, Priority: Low
- status: DONE

## issue0105
Allow more than one connection reference with node definition
11.01.2012 10:35:58 (de.abg.reichert.joerg): class Goal :
container ( fill = yellow ) {
text ( ) { name };
}
references {
subgoals : connection ();
strategies : connection ();
}
behavior {
create into goals palette &quot;Goals&quot;;
}
At the second connection reference a duplicate error is raised. Reason is, that the connection objects have no unique identifier.
15.01.2012 13:41:01 (de.abg.reichert.joerg): Fixed QualifiedNameProvider to identify Connection References not only by the connection but also considering the parent MetaReference. Tests are added.
Please note that references to containment references are not supported yet (actually the target of reference is not resolved (only eProxy URI) -> will be tracked in another issue (#108)).
- stakeholder: Spray user
- keywords: Type: Defect, Priority: High
- status: DONE

## issue0106
Code generator assumes fix name attribute at EClass instances
11.01.2012 10:38:14 (de.abg.reichert.joerg): Each of my classes has a &quot;identifier&quot; attribute. The resulting generated code has a method named &quot;getName&quot; which it balks at. If I change the generated code to &quot;getIdentifier&quot; then everything seems to be OK. These are typically in the
diagramCreateCLASSNAMEFeatureBase.java file.
example code in CreateShapeFeature.xtend:
def generate_createModelElement (MetaClass metaClass) '''
«val diagram = metaClass.diagram»
«val modelClassName = diagram.modelType.javaInterfaceName.shortName»
«val containmentRef = metaClass.behaviorsList.filter(typeof(CreateBehavior)).head.containmentReference»
/**
* Creates a new {@link «metaClass.name»} instance and adds it to the containing type.
*/
protected «metaClass.name» create«metaClass.visibleName»(ICreateContext context) {
// ask user for «metaClass.visibleName» name
String newName = SampleUtil.askString(TITLE, USER_QUESTION, &quot;&quot;);
if (newName == null || newName.trim().length() == 0) {
return null;
}
// create «metaClass.name» instance
«metaClass.name» newClass = «metaClass.EFactoryInterfaceName.shortName».eINSTANCE.create«metaClass.name»();
newClass.setName(newName);
// add the element to containment reference
«modelClassName» model = modelService.getModel();
«IF containmentRef.many»
model.get«containmentRef.name.toFirstUpper»().add(newClass);
«ELSE»
model.set«containmentRef.name.toFirstUpper»(newClass);
«ENDIF»
setDoneChanges(true);
return newClass;
}
'''
15.01.2012 18:01:01 (de.abg.reichert.joerg):
22.01.2012 17:35:48 (de.abg.reichert.joerg): Introduced key word 'askFor' to be able to specify for which attribute of the domain an input dialog should be shown.
import BusinessDomainDsl.*
diagram mydiagram for BusinessDomainModel
class BusinessClass:
container ( fill=dark_green )
{
text ( ) { "<<"+eClass.name+">> " + name};
}
behavior {
// Enable create feature for this class and add it to the palette "Shapes"
create into types palette "Shapes" askFor name;
}
Currently supported are String, Double and Integer attributes.
If nothing is specified, the logic for showing the input dialog is not generated.
- stakeholder: Spray user
- keywords: Type: Defect, Priority: High
- status: DONE

## issue0107
CreateConnectionFeature List in FeatureProvider lacks comma
11.01.2012 10:40:14 (de.abg.reichert.joerg): def generate_getCreateConnectionFeatures (Diagram diagram) '''
«overrideHeader»
public ICreateConnectionFeature[] getCreateConnectionFeatures() {
return new ICreateConnectionFeature[] {
«FOR cls : diagram.metaClasses.filter(e|e.representedBy instanceof Connection) SEPARATOR &quot;,&quot;»
new «cls.createFeatureClassName.shortName»(this)
«ENDFOR»
«IF ! diagram.metaClasses.filter(e|e.representedBy instanceof Connection).isEmpty »
,
«ENDIF»
«FOR metaClass : diagram.metaClasses»
«FOR reference : metaClass.references.filter(ref|ref.representedBy != null) SEPARATOR &quot;,&quot;»
new «reference.createReferenceAsConnectionFeatureClassName.shortName»(this)
«ENDFOR»
«ENDFOR»
};
}
'''
When there are multiple references of the same kind there is no comma generated in the code.
15.01.2012 16:35:40 (de.abg.reichert.joerg): head + tail + BEFORE (as ITERATOR is not supported anymore in FOR loops) to produce the comma
- stakeholder: Spray user
- keywords: Type: Defect, Priority: High
- status: DONE

## issue0108
references to containments in the references { } section of a class are not supported yet
15.01.2012 13:40:26 (de.abg.reichert.joerg): In the following example the reference from BusinessClass to BusinessRule is a containment relationship. Used in the references { } section the target of the reference is only returned a proxy. A validation rule currently catches this case stating that containment connections are not supported yet.
But in future it should be possible to also support connections to containment features.
diagram test for BusinessDomainDsl.BusinessDomainModel
class BusinessDomainDsl.BusinessRule :
container () {
text () { name };
}
class BusinessDomainDsl.BusinessClass :
container () {
text () { name };
}
references {
superclass : connection ();
associationsTo : connection ();
businessRules : connection ();
}
(see /org.eclipselabs.spray.xtext.tests/model/validation/connection-02.spray)
28.09.2012 09:15:01 (joswarmer): I will take a look why this is not possible, in the original spray it was.
19.10.2012 18:49:57 (joswarmer): As this kind of container will be replaced by the new compartments in the shape DSL, this issue is no longer relevant.
- stakeholder: Spray user
- keywords: Type: Enhancement, Priority: Low
- status: DONE

## issue0109
[shapes] Add implicit import for java.lang
24.03.2012 13:07:19 (karsten.thoms): To pass a parameter of kind String the parameter must be qualified with &quot;java.lang.String&quot;.
It should be possible to refer to types from java.lang with their short name. To do so, the ImportedNamespaceAwareLocalScopeProvider must be subclassed and registered to the runtime module. The method to overload is getImplicitImports().
24.03.2012 13:36:33 (karsten.thoms): Add also import for org.eclipselabs.spray.styles
29.03.2012 19:52:11 (karsten.thoms): Fixed by registering own Local Scope Provider
- stakeholder: Spray user
- keywords: Type: Enhancement, Priority: Medium, Component: Language
- status: DONE

## issue0110
[style] Remove description attribute, use multi-line comment instead
24.03.2012 13:30:13 (karsten.thoms): I think it would be better to describe a style simply by a standard multiline comment.
style BlackAndWhiteStyle {
description = &quot;A style with white background and black foreground.&quot;
...
}
/** &quot;A style with white background and black foreground. */
style BlackAndWhiteStyle {
...
}
I guess the reason why it is an attribute is to use the description in the generator and validation. Actually this can be achieved also by injecting the IEObjectDocumentationProvider.
03.11.2012 19:34:57 (joswarmer): If this is used bu the generator and provides e.g. help messages, I consider this semantically part of the model and in that case I think the description field is quite ok.
That way comments are for the DSL developer to explain the model and the description attribute is for the end-users. Different things for different purposes.
19.11.2012 15:02:57 (joswarmer): This is not an issue, but works as it should.
- stakeholder: Spray user
- keywords: Type: Enhancement, Priority: Medium, Component: Language
- status: DONE

## issue0111
Shape Formatter
28.03.2012 23:55:08 (chr.kastner): It seems Shape Formatter is currently not implemented
<b>What steps will reproduce the problem?</b>
1. Create Shape
2. Trigger Format
<b>What is the expected output? What do you see instead?</b>
I expect a nicely formatted shape, I see the response of the default formatter (one large line, each token separated with a space -- very ugly)
<b>What version of the product are you using? On what operating system?</b>
SPRAY 0.4.0
Mac OSX
<b>Please provide any additional information below.</b>
29.03.2012 15:46:12 (karsten.thoms): Yes, the formatter has not been implemented yet.
31.03.2012 13:25:36 (fabio.filippelli): Initiated by Karsten... i finalized it.
Please Retest!
02.04.2012 00:32:49 (karsten.thoms): This issue was closed by revision d1e4c247aa4b.
02.04.2012 00:33:30 (karsten.thoms): Done some last changes, considering as fixed now.
- stakeholder: Spray user
- keywords: Type: Defect, Priority: Medium
- status: DONE

## issue0112
Shape Outline
28.03.2012 23:58:48 (chr.kastner): Shape Outline shall show more than &quot;&lt;unnamed&gt;&quot;
<b>What version of the product are you using? On what operating system?</b>
SPRAY: 0.4.0
ECLIPSE: 3.7.2
OS: Mac OSX 10.7.3
19.11.2012 14:14:50 (joswarmer):
19.11.2012 14:59:31 (joswarmer):
19.11.2012 14:59:39 (joswarmer): This issue was closed by revision e637e817fb8a.
- stakeholder: Spray user
- keywords: Type: Defect, Priority: Medium
- status: DONE

## issue0113
SPRAY imports are not verified
29.03.2012 00:03:20 (chr.kastner): imports in a .spray file are not verified.
<b>What steps will reproduce the problem?</b>
1. create spray files
2. import a.b.c
<b>What is the expected output? What do you see instead?</b>
Error 'a.b.c.' does not exist! Currently no error marker.
<b>What version of the product are you using? On what operating system?</b>
SPRAY: 0.4.0
ECLIPSE: 3.7.2
OS: Mac OSX 10.7.3
<b>Please provide any additional information below.</b>
29.03.2012 15:45:01 (karsten.thoms): I think we should have a look at the Xtend implementation. Xtend offers error and warnings for non-existing / not used imports.
03.04.2012 15:49:31 (karsten.thoms): This issue was closed by revision 385dce00ef03.
03.04.2012 15:50:02 (karsten.thoms): See solution here: http://kthoms.wordpress.com/2012/04/03/jvmtype-import-check/
- stakeholder: Spray user
- keywords: Type: Defect, Priority: Medium
- status: DONE

## issue0114
Shape parameters shall be used in any assignment
29.03.2012 00:09:40 (chr.kastner): shape FormShape(java.lang.String formqualified) {
rectangle {
position(x=0,y=0)
size(width=60,height=20)
text {
align(horizontal=center, vertical=middle)
position(x=5, y=5)
size(width=60,height=20)
value=formqualified
}
}
}
Currently it is not possible to use a supplied parameter for position, width etc.
Really nice would be:
shape FormShape(java.lang.String formqualified, java.lang.Integer shapewidth) {
rectangle {
position(x=0,y=0)
size(width=shapewidth,height=20)
text {
align(horizontal=center, vertical=middle)
position(x=5, y=5)
size(width=shapewidth,height=20)
value=formqualified
}
}
}
I'm aware of, that isn't that easy and raises further issues. On the other hand it opens many possibilities.
12.11.2012 16:20:14 (joswarmer):
12.11.2012 18:00:00 (joswarmer):
- stakeholder: Spray user
- keywords: Type: Enhancement, Priority: Low
- status: OPEN

## issue0115
Support arithmetic operations within shapes
29.03.2012 00:12:49 (chr.kastner): shape FormShape(java.lang.String formqualified) {
rectangle {
position(x=0,y=0)
size(width=60,height=20)
text {
align(horizontal=center, vertical=middle)
position(x=5, y=5)
size(width=60,height=20)
value=formqualified
}
}
}
Currently width etc are all integer constants. Nice would be to use arithmetic expressions. This would be very handy on complexer Shapes.
12.11.2012 16:18:50 (joswarmer):
- stakeholder: Spray user
- keywords: Type: Enhancement, Priority: Low
- status: OPEN

## issue0116
Access to Graphiti Diagram Units
29.03.2012 00:13:29 (chr.kastner): It would be very handy to have access to Graphiti Diagram Units.
12.11.2012 16:20:32 (joswarmer):
- stakeholder: Spray user
- keywords: Type: Enhancement, Priority: Medium
- status: OPEN

## issue0117
Nested Shaped References
29.03.2012 00:28:13 (chr.kastner): It would be very handy to have nested Shape References (Reuse of already defined shapes, or even externally defined shapes -- or even reference Shape Libraries)
shape A {
}
shape B {
}
shape C {
shape A {
assignments
}
shape B {
assignments
}
}
28.09.2012 09:16:26 (joswarmer): Will be added as part iof adding containers to shapes
12.11.2012 16:20:56 (joswarmer):
- stakeholder: Spray user
- keywords: Type: Enhancement, Priority: Medium
- status: OPEN

## issue0118
Allow import in shapes
29.03.2012 01:00:58 (chr.kastner): shape A(java.lang.String param) {
}
vs.
import java.lang.String
shape A(String param) {
}
improves in my opinion readability and acceptance.
29.03.2012 14:45:00 (karsten.thoms):
- stakeholder: Spray user
- keywords: Type: Defect, Priority: Medium
- status: DONE

## issue0119
icon path shall be relative to project root
29.03.2012 11:09:26 (chr.kastner): class &lt;ModelElem&gt; icon &quot;icons/somedir/somegif.gif&quot; results to a warning, not to an error, stating &quot;Icon 'icons/icons/somedir/somegif.gif' not found.
Two issues:
(a) 'icons' directory shall not be assumed
(b) when file referene does not exist, it is an error, not a warning
29.03.2012 15:41:43 (karsten.thoms): I think the warning level is exact right. There are not many cases where warnings make sense, but this is one. The error would prevent the builder to run, but actually the "error" is just that the image provider points to a non-existing (not yet) image, and the this results just that the image is not displayed. This is indeed just worth a warning. It breaks nothing, but you likely want to fix it.
Regarding the icon path I am unsure whether this is a reasonable requirement. Could you explain why you want to put icons somewhere else? You would need to keep also in mind to add the icons to the build.properties, which is already prepared by the project wizard and you don't have to care of. The only thing is to put the images below a prepared path.
I am closing this one as won't fix. Please reopen when you have arguments why you think the current approach is not sufficient.
29.03.2012 20:33:32 (chr.kastner): Here are two issues:
(a) 'icons' directory shall not be assumed
Which is not really an effort
(b) 'warning' vs. 'error'
When a icon is missing, e.g. it has not been checked a ci build will not fail, what it should, a missing symbol results in non-shipping product, even an automatic test would not discover this situation!
How many developers look at warnings, not that much, I'm professional developer for more than 20 years, and I know many, many developers never ever looking at warnings!
I'm aware thru' an error, that the builder will not run, and in my opinion it should not, even it just an icon! Yes the resulting designer still works in its core, of course, but even you discover it in a manual test, you need another (hotfix) build, when such a trivial issue can easily be discovered.
Maybe others seeing it differently, however different organisation have different rules, maybe it could be a workspace setting!
If you like, you can split it in two issues!
- stakeholder: Spray user
- keywords: Type: Defect, Priority: Medium
- status: DONE

## issue0120
Style: Font-Selector shall also define selected size
29.03.2012 11:33:47 (chr.kastner): Font-Selector is nice, but it should also define font-size etc. if data is available, which may not be the case on all plattforms, but shall not override existing values.
12.11.2012 17:52:51 (joswarmer):
- stakeholder: Spray user
- keywords: Type: Enhancement, Priority: Medium
- status: OPEN

## issue0121
Shape: Image support is missing
29.03.2012 16:39:42 (chr.kastner): There is not image support within shapes.
shape &lt;ShapeIdent&gt; {
image {
...
}
}
or
shape &lt;ShapeIdent&gt; {
image(...)
}
24.09.2012 18:47:56 (de.abg.reichert.joerg): The following code that is currently manuelly to write should be generated:
http://groups.google.com/group/spray-users/msg/1b3856103b6c7353
12.11.2012 17:53:09 (joswarmer):
20.05.2013 15:40:11 (de.abg.reichert.joerg):
- stakeholder: Spray user
- keywords: Type: Enhancement, Priority: Medium
- status: READY

## issue0122
Shape settings have no effect
29.03.2012 17:12:14 (chr.kastner): shape &lt;IDENT&gt; {
size-min(width=180,height=40)
size-max(width=300,height=40)
stretching(horizontal=true,vertical=false)
proportional=true
}
The order of these assignments shall be any sequence, not dictated by grammar. I'm aware of, when they are free in sequence, they may be multiple, but this resolveable thru verification.
However these four assignments shall be part of 'Shape' itself, which would give the possibility of very fine grain resizing, e.g. one part of the compound shape is fixed and they other parts are sizeable.
However, when one these assignments are applied in the wrong order, there are no more XText proposals, which is rather irretating.
03.11.2012 19:33:02 (joswarmer): Your are right about the order, and Xtext dos have the functionality to make them any order while still allowing only one of each. Will pick this up.
Setting these properties on all sun elements is nice, but quite a big change. The new compartment functionality in the Shape DSL allows some of this, I will take a look whether this scenario can be supported.
12.11.2012 18:03:20 (joswarmer): The order of the size-min, size-max, stretching and proportional is not fixed. I thik the width and height are ok to be fixed, but we can make them variable as well.
19.11.2012 10:35:39 (joswarmer): probabl;y caused by Graphiti issue : https://bugs.eclipse.org/bugs/show_bug.cgi?id=352542
Styles in Graphiti only apply when the default value in the shape is unset.
In Graphiti 0.9 we should use PlainCreate methods for shapes, which will not set default values in the shapes.
19.11.2012 12:22:33 (joswarmer): Fixed this by using createPlain methods. Note however that the default transparency of 1.0 was in correct, 1.0 means full transparent. This was not noticed because this value was never applied. It now is.
Also note that text in most cases needs to have a style with the background-color set to transparent, or it will show as an ugly block inside the shape. As we now use the createPlain* methods, style values for all shapes have no default anymore. Because of this I think it is wise to ensure that the DefaultSprayStyle is used whenever there is no value specified for a style property..
- stakeholder: Spray user
- keywords: Type: Enhancement, Priority: Medium
- status: DONE

## issue0123
Make generator extensible without need to change the source
29.03.2012 18:01:06 (karsten.thoms): Spray's code generator produces a useful default implementation, and the generated code is extensible by the appliance of the generation gap pattern. This basically allows users to already customize code in the required way.
However, when a change is due to a structural insufficiency of the generator, the user would be forced to extend every single class, or change the source of the Graphiti generator plugin.
Therefore it should be possible to extend the generator itself without the means to touch its original source. Since Spray uses Xtend and Guice injection all what is needed is that the user derives their changed templates from Spray's one and provide a Guice configuration that registers the derived templates.
The only problem is to get Spray's code generator to respect a custom Guice module to override the existing one. To do so, an extension point is required to plug it into the UI.
29.03.2012 19:28:56 (karsten.thoms): This issue was closed by revision d47b3de34c4b.
29.03.2012 19:51:05 (karsten.thoms): Done and documented usage in User Guide.
A new example project was added as reference:
examples/generatorextension/org.eclipselabs.spray.generator.graphit
- stakeholder: Spray user
- keywords: Type: Defect, Priority: Medium
- status: DONE

## issue0124
Spray Generators do not respect genmodel settings
30.03.2012 15:01:59 (chr.kastner): When in a genmodel definition, settings Interface/Class Prefixes are done, they do not reflect in generated classes.
SPRAY-File:
(a) false imports
(b) Interface type names are used instead of model type
Model Type Name: Expression
Interface type Name: IExpression
generated: import &lt;qualified&gt;.IExpression.*
should be import &lt;qualified&gt;.Expression
same applies to 'classes'
Generated Files:
(a) model type names are used, instead of Interface type names
Model Type Name: Foo
Interface type name: IFoo
generated: Foo
should be: IFoo
This is almost a show stopper!
12.04.2012 22:40:39 (karsten.thoms):
23.04.2012 20:07:49 (karsten.thoms): Refactored all templates:
- added NamingExtensions#getItfName()
- changed Interface Class Pattern in BusinessDomainDsl.genmodel to I${0} to prefix interfaces by "I"
- resolved compile problems arising by using NamingExtensions#getItfName() where necessary
- stakeholder: Spray user
- keywords: Type: Defect, Priority: Medium
- status: DONE

## issue0125
Installation instructions
10.04.2012 16:43:08 (buettner.mail): <b>What steps will reproduce the problem?</b>
1. Download Eclipse Indigo Classic.
2. Add http://spray.eclipselabs.org.codespot.com/git.distribution/releases as an update site.
3. Select all.
4. Press next and then finish.
What is the expected output?
A successful install.
What do you see instead?
Cannot complete the install because one or more required items could not be found.
Software being installed: Spray SDK Feature 0.4.0.v20120319-1152 (org.eclipselabs.spray.feature.sdk.feature.group 0.4.0.v20120319-1152)
Missing requirement: Styles Model 0.4.0.v20120319-1152 (org.eclipselabs.spray.styles 0.4.0.v20120319-1152) requires 'bundle org.eclipse.xtext [2.2.0,2.3.0)' but it could not be found
Cannot satisfy dependency:
From: Spray Example &quot;One&quot; - Language Tests 0.4.0.v20120319-1152 (org.eclipselabs.spray.examples.one 0.4.0.v20120319-1152)
To: bundle org.eclipselabs.spray.styles 0.4.0
Cannot satisfy dependency:
From: Spray SDK Feature 0.4.0.v20120319-1152 (org.eclipselabs.spray.feature.sdk.feature.group 0.4.0.v20120319-1152)
To: org.eclipselabs.spray.examples.one [0.4.0.v20120319-1152]
<b>What version of the product are you using? On what operating system?</b>
I'm using Eclipse SDK 3.7.2 (Classic, 64bit).
My operating system is Windows 7 64bit Professional.
<b>Please provide any additional information below.</b>
https://spray.ci.cloudbees.com/job/spray-ci-build/lastSuccessfulBuild/artifact/releng/org.eclipselabs.spray.repository/target/repository/ doesn't work either
13.04.2012 09:06:27 (de.abg.reichert.joerg): The correct third party repository URL is:
https://spray.ci.cloudbees.com/job/spray-ci-targetplatform/lastSuccessfulBuild/artifact/releng/org.eclipselabs.spray.repository/target/repository/
Add this as update site and then add the normal update site:
https://spray.ci.cloudbees.com/job/spray-assembly-build/lastSuccessfulBuild/artifact/releng/org.eclipselabs.spray.updatesite/target/repository/
13.04.2012 11:16:18 (de.abg.reichert.joerg): Fixed with Commit 75f96183ef259b69b74da2d32414e52850fb5e16 and Commit 14351ada263b53bfe01f2eaaae5df6c2fe3963d5
Already included in
https://spray.ci.cloudbees.com/job/spray-docs-build/
Should be available with the next nightly assembly build.
- stakeholder: Spray user
- keywords: Type: Defect, Priority: Medium
- status: DONE

## issue0126
askFor has no effect for connections
13.04.2012 09:38:53 (de.abg.reichert.joerg): When adding a connection in the generated diagram editor there does not appear the dialog for setting the initial property despite of the defined askFor property in the Spray DSL
15.04.2012 23:15:45 (de.abg.reichert.joerg): Fixed with Commit b5019dba397ac2cb6638e8ea75d4bce979e8a184
- stakeholder: Spray user
- keywords: Type: Defect, Priority: Medium
- status: DONE

## issue0127
Couldn't resolve reference to root EClass of a model
13.04.2012 15:14:08 (janreimone): After creating a Spray project with the wizard a clean Spray file is generated. According to the input I made in the wizard a root metaclass is defined as root visiual class. The problem is that I get the error annotated saying that the EClass could not be resolved. I tried it with my own metamodels and with Ecore. For Ecore the following error occurs:
Couldn't resolve reference to EClass 'EPackage'.
The default import for Ecore is:
import ecore.*
which I have changed to:
import org.eclipse.emf.ecore.*
Furthermore, the plugin org.eclipse.emf.ecore is referenced as required in the MANIFEST.MF file. What is the matter? What can I do to get the metaclasses resolved?
15.04.2012 15:40:49 (de.abg.reichert.joerg): I can confirm this bug:
How to reproduce:
* Install Spray in a Eclipse Classic 3.7.2
* Create a new Spray Project via wizard
Variant 1: Use EMF model from installed plug-in, i.e. EMF registry
* Use "Browse registered packages" and choose a URI
Variant 2: Use EMF model from local EMF project
* Create Empty EMF project
* Create Ecore file
* Create EMF Generator Model
* export Genmodel via plugin.xml
* Use "Browse workspace" in Spray wizard and choose Ecore file
Variant 3: Use EMF model from within Spray project
* Use Variant 2 first and then adapt the Spray project
* Create Ecore file
* Create EMF Generator Model
In all 3 variants the referenced EClass cannot be resolved in the Spray DSL.
The only work around is to use Spray as Eclipse runtime started from the development workspace.
15.04.2012 15:48:15 (de.abg.reichert.joerg): post scriptum: When using the runtime workspace there is also the need to import(=copy) the mm project into the workspace.
16.04.2012 14:16:29 (karsten.thoms): OK, I will investigate this when finding some time again.
23.04.2012 22:38:33 (karsten.thoms): Found an indication why Ecore models may not get indexed when they are from the development workspace.
http://www.eclipse.org/forums/index.php/m/854255/#msg_854255
24.04.2012 00:45:47 (karsten.thoms): Replaced JdtToBeBuiltComputer with custom implementation JdtToBeBuiltComputerExt. Added new project org.eclipselabs.spray.runtime.xtext.ui.
24.04.2012 10:32:10 (janreimone): are these changes available from the stable build update site?
25.04.2012 09:11:51 (karsten.thoms): Yes, from the CI update site
https://spray.ci.cloudbees.com/job/spray-assembly-build/lastSuccessfulBuild/artifact/releng/org.eclipselabs.spray.updatesite/target/repository/
Joerg Reichert gave feedback that he did not recognize the solution, but maybe you could confirm this.
Sebastian Zarnekow replied in the forum that this goes actually down to a p2 bug.
After update you should have the new plugin org.eclipselabs.spray.runtime.xtext.ui installed.
25.04.2012 14:56:45 (janreimone): I checked it. Same situation as before.
25.04.2012 15:11:47 (janreimone): addition: the workaround described by Jörg doesn't work for me either.
25.04.2012 18:11:45 (karsten.thoms): Anyway, thanks for the feedback. I'll try to find another workaround.
12.05.2012 03:09:41 (elldekaa): The 'juno' branch has the same issue.
14.05.2012 10:12:08 (de.abg.reichert.joerg): In response to comment #9: The workaround using the runtime workspace started from the development workspace works, if you exclude the log4j 2.0.13 dependency in the launcher configuration. If you do not exclude it a class loader exception is thrown when invoking the auto completion as Xtext has got a hard dependency to log4j 2.0.15 but when both log4j 2.0.13 and log4j 2.0.15 are included in the runtime some refletion mechanism get mixed up with the versions. I included the launcher configuration in the spray.xtext project on the Juno branch.
14.05.2012 10:16:41 (de.abg.reichert.joerg): In response to comment #12: I can confirm this with the latest repository builds that uses Xtext 2.3M7
3rd party:
https://spray.ci.cloudbees.com/job/spray-ci-targetplatform-juno/lastSuccessfulBuild/artifact/releng/org.eclipselabs.spray.repository/target/repository/
Spray Juno Update Site:
https://spray.ci.cloudbees.com/job/spray-assembly-build-juno/ws/releng/org.eclipselabs.spray.updatesite/target/repository/
14.05.2012 10:23:00 (de.abg.reichert.joerg): We should rework the scoping / the content assist of the imported domain objects in the way that
* at diagram level only EClasses are proposed
** that are contained within the EPackages declared in the import section (currently everything from the classpath is proposed) (maybe also classes that extends EClasses from the EPackage as well)
** that have at least one containment reference (without containments they are not usable as root for the meta class definitions to come)
* at diagram level only EClasses are proposed
** that are used in containment relationships of the EClass defined at the diagram level
23.05.2012 15:43:48 (dsimkins123): Dear All,
Is there an update to this issue? I too am stuck unable to create a spray project!
Kind regards
Dan
04.06.2012 00:03:01 (de.abg.reichert.joerg): This issue was closed by revision 62cbeded3e68.
07.06.2012 16:35:28 (de.abg.reichert.joerg):
The fix from the juno branch have to applied to the indigo branch as well.
14.06.2012 14:31:42 (arunbnair): When will this fix be available on the indigo branch?
15.06.2012 09:31:06 (de.abg.reichert.joerg): Now the indigo branch includes the fix:
https://spray.ci.cloudbees.com/job/spray-assembly-build/lastSuccessfulBuild/artifact/releng/org.eclipselabs.spray.updatesite/target/repository/
If you want to use Juno, this is also available now:
3rd party repository:
https://spray.ci.cloudbees.com/job/spray-ci-targetplatform-juno/lastSuccessfulBuild/artifact/releng/org.eclipselabs.spray.repository/target/repository/
Spray update site:
https://spray.ci.cloudbees.com/job/spray-assembly-build-juno/ws/releng/org.eclipselabs.spray.updatesite/target/repository/
- stakeholder: Spray user
- keywords: Type: Defect, Priority: Critical
- status: DONE

## issue0128
Spray update site doesn't work anymore
26.04.2012 16:28:55 (CMordant1): Update site
<b>What steps will reproduce the problem?</b>
1. add a new software site in eclipse with the urls of spray
<b>What is the expected output? What do you see instead?</b>
Spray bundles to download are expected but in place an error message saying there are no repository here is displayed
<b>What version of the product are you using? On what operating system?</b>
eclipse x86 3.7, windows XP
Best regards
26.04.2012 16:41:21 (CMordant1): sorry, I had my proxy configuration disabled
30.04.2012 13:18:32 (karsten.thoms):
- stakeholder: Spray user
- keywords: Type: Defect, Priority: Medium
- status: DONE

## issue0129
Installation into Eclipse Juno
27.04.2012 16:54:24 (elldekaa): <b>Choose a Component label.</b>
<b>What steps will reproduce the problem?</b>
1. Install last version of Eclipse Juno
2. Add nightly update sites of spray
3. Launch the installation of spray sdk
<b>What is the expected output? What do you see instead?</b>
I get the following dependancies errors:
--------------------------
Cannot complete the install because of a conflicting dependency.
Software being installed: Spray SDK Feature 0.5.0.201204250010 (org.eclipselabs.spray.feature.sdk.feature.group 0.5.0.201204250010)
Software currently installed: Xtext SDK 2.3.0.v201203201034 (org.eclipse.xtext.sdk.feature.group 2.3.0.v201203201034)
Only one of the following can be installed at once:
Xtext UI Core 2.0.1.v201108020636 (org.eclipse.xtext.ui 2.0.1.v201108020636)
Xtext UI Core 1.0.2.v201102150722 (org.eclipse.xtext.ui 1.0.2.v201102150722)
Xtext UI Core 2.1.1.v201111141332 (org.eclipse.xtext.ui 2.1.1.v201111141332)
Xtext UI Core 2.3.0.v201203201034 (org.eclipse.xtext.ui 2.3.0.v201203201034)
Xtext UI Core 2.2.1.v201112130541 (org.eclipse.xtext.ui 2.2.1.v201112130541)
Cannot satisfy dependency:
From: Xtext SDK 2.3.0.v201203201034 (org.eclipse.xtext.sdk.feature.group 2.3.0.v201203201034)
To: org.eclipse.xtext.ui.feature.group [2.3.0.v201203201034]
Cannot satisfy dependency:
From: Xtext UI 2.3.0.v201203201034 (org.eclipse.xtext.ui.feature.group 2.3.0.v201203201034)
To: org.eclipse.xtext.ui [2.3.0.v201203201034]
Cannot satisfy dependency:
From: Spray SDK Feature 0.5.0.201204250010 (org.eclipselabs.spray.feature.sdk.feature.group 0.5.0.201204250010)
To: org.eclipselabs.spray.xtext.tests [0.5.0.201204250010]
Cannot satisfy dependency:
From: Spray Example &quot;One&quot; - Language Tests 0.5.0.201204250010 (org.eclipselabs.spray.xtext.tests 0.5.0.201204250010)
To: bundle org.eclipselabs.spray.xtext.ui 0.5.0
Cannot satisfy dependency:
From: Spray Language UI 0.5.0.201204250010 (org.eclipselabs.spray.xtext.ui 0.5.0.201204250010)
To: bundle org.eclipse.xtext.ui [2.2.0,2.3.0)
--------------------------
<b>What version of the product are you using? On what operating system?</b>
Last nightly build / Updated eclipse juno / Ubuntu 12.04 (64 bits)
<b>Please provide any additional information below.</b>
30.04.2012 13:16:28 (karsten.thoms): Xtext based language are very closely coupled to a specific Xtext version. Spray is built against Xtext 2.2.1, which is the latest official release. It is strongly required that this version of Xtext is used, and we enforce this in our bundle manifests. Also the user guide states that this version is required. Spray won't be compatible against 2.3.0.
Spray will upgrade to Xtext 2.3.0 when released.
03.05.2012 07:06:00 (karsten.thoms): Opened branch "eclipse_juno".
Migrated target platform. Fixed dependency issues and other compile problems.
03.05.2012 09:16:11 (karsten.thoms): Created CI Job for Juno Target Platform. Repository is available now:
https://spray.ci.cloudbees.com/job/spray-ci-targetplatform-juno/lastSuccessfulBuild/artifact/releng/org.eclipselabs.spray.repository/target/repository/
03.05.2012 10:00:34 (elldekaa): Thanks a lot !
I tried this new update site but it seems to contain only the 3rd party tools... Did I miss something ?
03.05.2012 22:37:47 (elldekaa): Ok, I just figured that all builds of spray have failed...
04.05.2012 01:23:45 (karsten.thoms): Work is in progress. This was just the first step.
- Built and deployed xtend-maven-plugin:2.3.0-M6 & org.eclipse.xtend:org.eclipse.xtend.standalone:2.3.0-M6 to Fornax repo.
- fixed dependencies to Maven plugin
- fixing tests
- fixed compilation problem
04.05.2012 06:24:15 (karsten.thoms): First build running. Update site:
https://spray.ci.cloudbees.com/job/spray-assembly-build-juno/lastSuccessfulBuild/artifact/releng/org.eclipselabs.spray.updatesite/target/repository
13.08.2012 22:38:48 (karsten.thoms): Juno branch is now master and primary build:
https://spray.ci.cloudbees.com/job/spray-assembly-build-juno/lastSuccessfulBuild/artifact/releng/org.eclipselabs.spray.updatesite/target/repository
22.08.2012 01:06:53 (de.abg.reichert.joerg): the installation of the Juno version works now (tested with Eclipse Classic 4.2 I20120608-1400 64bit under Windows 7 64bit):
3rd: https://spray.ci.cloudbees.com/job/spray-ci-targetplatform/lastSuccessfulBuild/artifact/releng/org.eclipselabs.spray.repository/target/repository/
Spray: https://spray.ci.cloudbees.com/job/spray-assembly-build/54/artifact/releng/org.eclipselabs.spray.updatesite/target/repository/
- stakeholder: Spray user
- keywords: Type: Defect, Priority: Medium
- status: DONE

## issue0130
Add SVG Shape Generator
04.05.2012 07:57:50 (karsten.thoms): The Shapes DSL provides good abstraction to define shapes. However, complex shapes are a bit hard to design, since a restart is required to visualize the target shape.
To reduce this roundtrip a preview of the shape can be visualized by rendering an SVG image. This can be viewed with the Internal Web Browser. Later maybe integrated in the Outline View or a Preview View.
Work started, see screenshot for first example.
14.10.2012 22:35:43 (de.abg.reichert.joerg): SVGs for Shapes, also for shapes with compartments can be generated now. Any improvements to the Shape SVG generator (like including Style information) should be tracked in separate issues.
- stakeholder: Spray user
- keywords: Type: Enhancement, Priority: Medium, Component: Codegen
- status: DONE

## issue0131
Reduce plugin dependencies of Spray diagram plugin
07.05.2012 21:26:53 (karsten.thoms): The code produced by the Shapes and Styles generator produces classes that implement framework interfaces/classes that are part of the DSL plugins. This currently means that the produced diagram plugin must have a dependency on the Shape/Style DSL plugins themselve.
The produced code must be independent of the language implementation. For runtime framework classes the o.e.s.runtime.* plugins are there.
These framework classes must be moved to org.eclipselabs.spray.runtime.graphiti:
- ISprayStyle
- DefaultSprayStyle
- ISprayShape
- DefaultSprayShape
Code generator templates must be adjusted.
07.05.2012 22:26:44 (karsten.thoms): Need also to move these classes:
- ISprayConnection
- DefaultSprayConnection
- ISprayShapeConstants
- SprayLayoutManager
Changed generator templates:
- StyleGenerator
- GeneratorShapeDefinition
- GeneratorConnectionDefinition
Changed project wizard to not include the DSL plugins in the manifest of newly generated projects. (SprayProjectCreator)
Further figured out that a dependency to org.eclipse.xtext.ui only exists because we need 1 class from it. Copied AbstractGuiceAwareExecutableExtensionFactory and removed dependency.
07.05.2012 22:33:35 (karsten.thoms): Dependency to org.eclipse.xtext.ui is also needed for other purposes (e.g. IURIEditorOpener), need to leave the dependency.
07.05.2012 22:43:37 (karsten.thoms): Consolidated constants from ISprayShapeConstants into ISprayConstants. One interface is enough.
14.05.2012 21:37:07 (karsten.thoms): Code refactoring finished.
- stakeholder: Spray user
- keywords: Type: Defect, Priority: Medium
- status: DONE

## issue0132
Develop Spray Diagram for Shapes DSL
09.05.2012 21:32:15 (karsten.thoms): I got already multiple times feedback that a visual editor for Shapes would be desired. And why not develop such an editor with Spray itself? It should be doable with Spray and a good proof by eating our own dogfood.
28.09.2012 09:18:40 (joswarmer): I doubt whetehr this is eating our own dogfood, this kind of editor is more like a cat, so our dogfood does not taste well.
In other words, I doyubt whether the domain for a shape design editor is within the scope of Spray.
12.11.2012 17:59:38 (joswarmer):
- stakeholder: Spray user
- keywords: Type: Task, Priority: Low
- status: OPEN

## issue0133
Switch from AbstractModelInferrer to IJvmDeclaredTypeAcceptor
14.05.2012 22:26:51 (de.abg.reichert.joerg): 5153 [Worker-2] ERROR org.eclipse.xtext.xbase.jvmmodel.AbstractModelInferrer - You are using a deprecated implementation of IjvmModelInferrer. Please change the type of the acceptor in your 'infer' method.
It should be 'org.eclipse.xtext.xbase.jvmmodel.IJvmDeclaredTypeAcceptor'.
This backward compatibility mode will be removed in the next release (2.3 June 2012).
04.06.2012 00:19:18 (de.abg.reichert.joerg): This issue was closed by revision 499c17bb9b62.
- stakeholder: Spray user
- keywords: Type: Enhancement, Priority: Medium
- status: DONE

## issue0134
Installation of Spray via Release Update Site fails because of missing dependencies
26.05.2012 18:36:53 (marvin.kampf): <b>Choose a Component label.</b>
<b>What steps will reproduce the problem?</b>
1. Eclipse Indigo 3.72 with Modeling Components on Mac OS X 10.7.4
2. Go to Help / Install New Software ... / Spray Release Update Site
3. Install Spray Feature and/or Spray Feature SDK
<b>What is the expected output? What do you see instead?</b>
Expected: Installation of Spray
Instead:
Cannot complete the install because one or more required items could not be found.
Software being installed: Spray SDK Feature 0.4.0.v20120319-1152 (org.eclipselabs.spray.feature.sdk.feature.group 0.4.0.v20120319-1152)
Missing requirement: Spray Language Runtime 0.4.0.v20120319-1152 (org.eclipselabs.spray.xtext 0.4.0.v20120319-1152) requires 'bundle org.eclipse.xtext.xtend2 [2.2.0,2.3.0)' but it could not be found
Cannot satisfy dependency:
From: Spray Example &quot;One&quot; - UI Tests 0.4.0.v20120319-1152 (org.eclipselabs.spray.examples.one.tests 0.4.0.v20120319-1152)
To: bundle org.eclipselabs.spray.runtime.graphiti 0.4.0
Cannot satisfy dependency:
From: Spray SDK Feature 0.4.0.v20120319-1152 (org.eclipselabs.spray.feature.sdk.feature.group 0.4.0.v20120319-1152)
To: org.eclipselabs.spray.examples.one.tests [0.4.0.v20120319-1152]
Cannot satisfy dependency:
From: Spray Runtime Plugin for Graphiti 0.4.0.v20120319-1152 (org.eclipselabs.spray.runtime.graphiti 0.4.0.v20120319-1152)
To: bundle org.eclipselabs.spray.xtext 0.0.0
<b>What version of the product are you using? On what operating system?</b>
Eclipse Indigo 3.72 with Modeling Components on Mac OS X 10.7.4
Graphiti 0.8.2
<b>Please provide any additional information below.</b>
15.06.2012 10:25:46 (jeansebastien.sottet): Hi,
An answer was given by Jörg Reichert in the Spray-dev group about this issue, and give a path to a second update site:
https://groups.google.com/forum/?fromgroups#!topic/spray-dev/Bde7WRaE6rU
This is due to the fact that spray update site does not contains the third party dependencies.
29.08.2012 22:49:13 (de.abg.reichert.joerg): Also documented in https://spray.ci.cloudbees.com/job/spray-docs-build/lastSuccessfulBuild/artifact/docs/org.eclipselabs.spray.doc.user/docs/html/SprayUserGuide.html#InstallSpray
For our next official release we should consider to build an all-in-update site, but the running snapshot update sites should stay to the pattern 3rd party update site and Spray update site to reduced build times and memory.
- stakeholder: Spray user
- keywords: Type: Defect, Priority: Medium
- status: DONE

## issue0135
Spray cannot resolve reference to JvmIdentifiableElements like eClass and name when using custom ecore
11.06.2012 16:30:35 (flatombe): Hi, here is the description of a problem I have with Spray 0.5 :
<b>What steps will reproduce the problem?</b>
1. Install Eclipse (Modeling), update the modeling component
2. Install Spray's third party and Spray from the CI update site (Spray SDK Feature 0.5.0.201206060013)
3. Create a new spray project, based on a self-made .ecore
4. Add the .ecore to the build path of the project
5. Uncomment the example class mapping (class BusinessClass icon ...) and replace &quot;BusinessClass&quot; with one of the classes from the .ecore used.
<b>What is the expected output? What do you see instead?</b>
The project raises errors :
- Couldn't resolve reference to JvmIdentifiableElements 'name'
- Couldn't resolve reference to JvmIdentifiableElements 'eClass'
- Couldn't resolve reference to EReference 'types'
<b>What version of the product are you using? On what operating system?</b>
Spray SDK Feature 0.5.0.201206060013
Eclipse modeling indigo SR2
Did I miss something ? I am particularly surprised that it seems to work with the proposed metamodel mod4j businessClass but once I use another one it seems to be lost.
Regards
13.06.2012 06:34:00 (de.abg.reichert.joerg): I think it is related to issue #127. This is fixed on the Juno branch, just take a look at the scope provider (for eClass at Diagram and MetaClass) and the proposal provider in the ui plugin (for the import proposal).
15.06.2012 09:31:56 (de.abg.reichert.joerg): should be fixed with fix of issue #127
- stakeholder: Spray user
- keywords: Type: Defect, Priority: Medium
- status: DONE

## issue0136
Xtext tests that do not suppress serialization fail on Windows
14.06.2012 21:54:10 (de.abg.reichert.joerg): <b>What steps will reproduce the problem?</b>
1. Run the ConnectionModelTest or ShapeModelTest as they do not suppress serialization
<b>What is the expected output? What do you see instead?</b>
* expected: expected and actual serialized DSL should be equal
* actual: expected and actual output differ in their line delimiter (see screenshot in appendix)
01.09.2012 10:19:00 (de.abg.reichert.joerg): Now tests are runnable under Windows, too. (Fixed by setting encoding and line delimiter for each project and converting test files with Notepad++ to UTF-8 BDM)
- stakeholder: Spray user
- keywords: Type: Defect, Priority: Medium, xtext-tests, serialization
- status: DONE

## issue0137
Unable to load ExecutableExtensionFactory
04.07.2012 08:41:23 (de.abg.reichert.joerg): Plug-in org.eclipselabs.spray.examples.busmod was unable to load class org.eclipselabs.spray.examples.busmod.internal.ExecutableExtensionFactory
<b>What steps will reproduce the problem?</b>
1. Create new Spray project
2. copy plugin.xml to root
3. start new runtime
4. create new diagram
<b>What is the expected output? What do you see instead?</b>
- should be: Working diagram
- but was: the exception above
29.08.2012 21:50:09 (de.abg.reichert.joerg): Not reproducable anymore with
* Spray SDK Feature 0.5.0.201208212210 (Juno)
* Spray SDK Feature 0.5.0.201208052205 (Indigo)
- stakeholder: Spray user
- keywords: Type: Defect, Priority: High
- status: DONE

## issue0138
Initially generated *DefaultStyle.java does not compile
04.07.2012 09:00:51 (de.abg.reichert.joerg): <b>What steps will reproduce the problem?</b>
1. Create new Spray project
<b>What is the expected output? What do you see instead?</b>
- should be: from the initial spray model compiling code should be generated
- but was: *DefaultStyle.java does not compile
Work-around:
- remove the style file and the reference to its content in the spray file
29.08.2012 21:57:58 (de.abg.reichert.joerg): In Spray SDK Feature 0.5.0.201208212210 (Juno) this has been fixed.
In Spray SDK Feature 0.5.0.201208052205 (Indigo) the file does not compile as the style project is not imported in the MANIFEST.MF by default.
29.08.2012 22:00:54 (de.abg.reichert.joerg):
01.09.2012 20:37:33 (de.abg.reichert.joerg):
- stakeholder: Spray user
- keywords: Type: Defect, Priority: Medium
- status: DONE

## issue0139
Install cannot be completed due to conflicting dependencies
04.07.2012 11:14:45 (de.abg.reichert.joerg):
Cannot complete the install because one or more required items could not be found.
Software being installed: Spray SDK Feature 0.5.0.201206302226 (org.eclipselabs.spray.feature.sdk.feature.group 0.5.0.201206302226)
Software currently installed: Xtext SDK 2.3.0.v201206120633 (org.eclipse.xtext.sdk.feature.group 2.3.0.v201206120633)
Missing requirement: Spray Generator Plugin for Graphiti 0.5.0.201205040004 (org.eclipselabs.spray.generator.graphiti 0.5.0.201205040004) requires 'bundle org.eclipse.graphiti 0.9.0' but it could not be found
Missing requirement: Spray Generator Plugin for Graphiti 0.5.0.201206302202 (org.eclipselabs.spray.generator.graphiti 0.5.0.201206302202) requires 'bundle org.eclipse.graphiti 0.9.0' but it could not be found
Only one of the following can be installed at once:
Xbase Model 2.0.1.v201108020636 (org.eclipse.xtext.xbase 2.0.1.v201108020636)
Xbase Model 1.0.2.v201102150722 (org.eclipse.xtext.xbase 1.0.2.v201102150722)
Xbase Model 2.1.1.v201111141332 (org.eclipse.xtext.xbase 2.1.1.v201111141332)
Xbase Model 1.0.1.v201008251220 (org.eclipse.xtext.xbase 1.0.1.v201008251220)
Xbase Model 2.3.0.v201206120633 (org.eclipse.xtext.xbase 2.3.0.v201206120633)
Xbase Model 1.0.0.v201006170321 (org.eclipse.xtext.xbase 1.0.0.v201006170321)
Xbase Model 2.0.0.v201106070531 (org.eclipse.xtext.xbase 2.0.0.v201106070531)
Xbase Model 2.2.1.v201112130541 (org.eclipse.xtext.xbase 2.2.1.v201112130541)
Cannot satisfy dependency:
From: Xtext SDK 2.3.0.v201206120633 (org.eclipse.xtext.sdk.feature.group 2.3.0.v201206120633)
To: org.eclipse.xtext.xbase.feature.group [2.3.0.v201206120633]
Cannot satisfy dependency:
From: Xbase 2.3.0.v201206120633 (org.eclipse.xtext.xbase.feature.group 2.3.0.v201206120633)
To: org.eclipse.xtext.xbase [2.3.0.v201206120633]
Cannot satisfy dependency:
From: Spray SDK Feature 0.5.0.201206302226 (org.eclipselabs.spray.feature.sdk.feature.group 0.5.0.201206302226)
To: org.eclipselabs.spray.xtext.tests [0.5.0.201206302226]
Cannot satisfy dependency:
From: Spray Generator Plugin for Graphiti 0.5.0.201206302226 (org.eclipselabs.spray.generator.graphiti 0.5.0.201206302226)
To: bundle org.eclipse.xtext.xbase [2.2.0,2.3.0)
Cannot satisfy dependency:
From: Spray Example &quot;One&quot; - Language Tests 0.5.0.201206302226 (org.eclipselabs.spray.xtext.tests 0.5.0.201206302226)
To: bundle org.eclipselabs.spray.generator.graphiti 0.5.0
I think this is the problem:
To: bundle org.eclipse.xtext.xbase [2.2.0,2.3.0)
This excludes 2.3.0, so it cannot be resolved - I have to update the dependencies declaration in org.eclipselabs.spray.generator.graphiti
29.08.2012 22:11:07 (de.abg.reichert.joerg): In Spray SDK Feature 0.5.0.201208212210 (Juno), all dependencies up to org.eclipse.xtext.xbase [2.3.0,2.4.0) now.
For Spray SDK Feature 0.5.0.201208052205 (Indigo) the range is still set to [2.2.0,2.3.0), that is ok, as Xtext 2.3 is released with Juno, and only Xtext 2.3 RC2 is compatible to Eclipse Indigo.
02.09.2012 11:23:23 (de.abg.reichert.joerg): discovered that the normal Eclipse update in Indigo allows installing Xtext 2.3.1. Thus the range of Xtext is now widen to [2.2.0, 2.4.0) for Spray Indigo,
28.04.2013 11:36:50 (ferryxo): unfortunately, the error is still to be found.
I use eclipse that is provided in your website.
Cannot complete the install because of a conflicting dependency.
Software being installed: Spray SDK Feature 0.5.0.201304222207 (org.eclipselabs.spray.feature.sdk.feature.group 0.5.0.201304222207)
Software currently installed: Xpect SDK Feature 0.1.0.201304120010 (org.xpect.sdk.feature.group 0.1.0.201304120010)
Only one of the following can be installed at once:
Xbase Model 2.4.0.v201303201134 (org.eclipse.xtext.xbase 2.4.0.v201303201134)
Xbase Model 2.0.1.v201108020636 (org.eclipse.xtext.xbase 2.0.1.v201108020636)
Xbase Model 1.0.2.v201102150722 (org.eclipse.xtext.xbase 1.0.2.v201102150722)
Xbase Model 2.1.1.v201111141332 (org.eclipse.xtext.xbase 2.1.1.v201111141332)
Xbase Model 2.3.0.v201206120633 (org.eclipse.xtext.xbase 2.3.0.v201206120633)
Xbase Model 2.3.1.v201208210947 (org.eclipse.xtext.xbase 2.3.1.v201208210947)
Xbase Model 2.4.1.v201304180855 (org.eclipse.xtext.xbase 2.4.1.v201304180855)
Xbase Model 2.2.1.v201112130541 (org.eclipse.xtext.xbase 2.2.1.v201112130541)
Cannot satisfy dependency:
From: Spray Example "One" - Language Tests 0.5.0.201304222207 (org.eclipselabs.spray.examples.one 0.5.0.201304222207)
To: bundle org.eclipselabs.spray.generator.graphiti 0.5.0
Cannot satisfy dependency:
From: Spray SDK Feature 0.5.0.201304222207 (org.eclipselabs.spray.feature.sdk.feature.group 0.5.0.201304222207)
To: org.eclipselabs.spray.examples.one [0.5.0.201304222207]
Cannot satisfy dependency:
From: Spray Generator Plugin for Graphiti 0.5.0.201304222207 (org.eclipselabs.spray.generator.graphiti 0.5.0.201304222207)
To: bundle org.eclipse.xtext.xbase [2.3.0,2.4.0)
Cannot satisfy dependency:
From: Xpect SDK Feature 0.1.0.201304120010 (org.xpect.sdk.feature.group 0.1.0.201304120010)
To: org.xpect.xtext.lib [0.1.0.201304120010]
Cannot satisfy dependency:
From: Lib 0.1.0.201304120010 (org.xpect.xtext.lib 0.1.0.201304120010)
To: bundle org.eclipse.xtext.xbase 2.4.0
28.04.2013 13:13:36 (de.abg.reichert.joerg): The Eclipse provided by our website is meant to be used by Spray developers. Normal Spray users should use a Eclipse 4.2.2 Classic and then add the Spray as well as the 3rd party update site.
- stakeholder: Spray user
- keywords: Type: Defect, Priority: High
- status: DONE

## issue0140
Shape preview in Xtext hover
08.07.2012 17:02:44 (de.abg.reichert.joerg): As addition to the SVG generator
http://code.google.com/a/eclipselabs.org/p/spray/issues/detail?id=130
the generated SVG file out of the shape definition should be shown inside the Xtext hover display when moving the mouse over the Shape definition respectively the Shape definition reference inside the Spray file.
For how to implement a Xtext rich hover, see:
http://ckulla.wordpress.com/2011/02/06/hover-support-in-xtext-2-0/
http://christiandietrich.wordpress.com/2011/07/16/hover-support-in-xtext-2-0-tutorial/
http://muelder.blogspot.de/2012/04/eclipse-user-help-in-your-xtext-hover.html
For how to show an SVG see:
http://sourceforge.net/projects/svgplugin/
http://help.eclipse.org/galileo/index.jsp?topic=/org.eclipse.gmf.doc/reference/api/tooling/org/eclipse/gmf/gmfgraph/SVGFigure.html
or loaded inside the SWTBrowser: http://dev.eclipse.org/viewcvs/viewvc.cgi/org.eclipse.swt.snippets/src/org/eclipse/swt/snippets/Snippet136.java?view=co
08.10.2012 21:05:36 (de.abg.reichert.joerg): Realized on Juno branch, see also mail: http://groups.google.com/group/spray-dev/msg/748188e9cef8b4c6
10.10.2012 19:21:48 (de.abg.reichert.joerg): migrated to indigo branch as well
- stakeholder: Spray user
- keywords: Type: Enhancement, Priority: Low
- status: DONE

## issue0141
Context menu entry "Show properties view" predefined
08.07.2012 17:11:07 (de.abg.reichert.joerg): A very common use case is to show the properties for a selected element in generated diagram editor.
When the properties is not opened yet you currently have to use Window -&gt; Show View -&gt; Others -&gt; General/Properties.
There should be a context menu entry available for every graphical element that should trigger to open respectively (re-)activate the properties view.
This context menu entry could be proposed as predefined custom behavior inside the Spray DSL editor.
20.05.2013 15:41:27 (de.abg.reichert.joerg):
- stakeholder: Spray user
- keywords: Type: Enhancement, Priority: Low
- status: READY

## issue0142
Enable linking to referenced domain model element
08.07.2012 17:14:56 (de.abg.reichert.joerg): In Spray DSL the linking (i.e. opening the editor with the domain model and jumping to the selected model element) is currently not possible (in all cases).
08.10.2012 21:05:55 (de.abg.reichert.joerg): Realized on Juno branch, see also mail: http://groups.google.com/group/spray-dev/msg/748188e9cef8b4c6
10.10.2012 19:22:07 (de.abg.reichert.joerg): migrated to indigo branch as well
- stakeholder: Spray user
- keywords: Type: Defect, Priority: Medium
- status: DONE

## issue0143
Migrated connection DSL template proposal to new syntax
08.07.2012 17:17:25 (de.abg.reichert.joerg): The template proposal for a connection inside the Spray DSL do not respect the new syntax for connection definitions (curly braces instead of colon)
01.09.2012 20:37:54 (de.abg.reichert.joerg):
- stakeholder: Spray user
- keywords: Type: Defect, Priority: Medium
- status: DONE

## issue0144
Fix create behavior template askFor reference
08.07.2012 17:19:13 (de.abg.reichert.joerg): The create behavior template proposal always uses invalid reference in askFor part.
02.09.2012 10:06:48 (de.abg.reichert.joerg): now a simple placeholder "askFor" is used
- stakeholder: Spray user
- keywords: Type: Defect, Priority: Medium
- status: DONE

## issue0145
Adapt Spray DSL formatter to syntax changes
08.07.2012 17:21:49 (de.abg.reichert.joerg): * add line break after source to target statement in connection definition
* add line break after shape reference inside container definition block
* ...
28.10.2012 09:29:27 (de.abg.reichert.joerg): Adadpted formatters and added formatter tests for each language. After each change to language the test models (unformatted and expected formatted) should be adapted accordingly. So good test driven adaption of the formatters is possible so.
* org.eclipselabs.spray.xtext.tests/src/org/eclipselabs/spray/xtext/formatting/SprayFormatterTest.java
* org.eclipselabs.spray.styles.tests/src/org/eclipselabs/spray/styles/tests/StyleFormatterTest.java
* org.eclipselabs.spray.shapes.tests/src/org/eclipselabs/spray/shapes/tests/ShapeFormatterTest.java
- stakeholder: Spray user
- keywords: Type: Defect, Priority: Low
- status: DONE

## issue0146
Include all example projects into the automated build
08.07.2012 17:30:47 (de.abg.reichert.joerg): Currently only org.eclipselabs.spray.examples.one is included.
The following projects have to be included:
* BPMN
* de.htwg.2012.bpmn.mm
* org.eclipselabs.spray.examples.bpmn
* LWC 2012
* de.htwg.2012.lwc.mm
* org.eclipselabs.spray.examples.lwc2012
* Petrinets
* de.htwg.petrinet.mm
* org.eclipselabs.spray.examples.petrinet
* Fowler DSL / Statemachine
What actions are required for the inclusion?
* mavenize projects
* add mwe2 Workflows for starting the generators (style, shape, spray)
* clean up and extend projects if necessary (Fowler DSL, styles and shapes in example.one)
A successful build of the example projects is always a helpful indicator of a working Spray.
* add to modules in releng pom
29.08.2012 22:18:53 (de.abg.reichert.joerg): status: currently *.example.one and *.examples.petrinet are automated, the automation of lwc2012 still hangs, as there is an issue discovered with JVM type references that are currently not resolved until generation of the Java classes (but this should be already resolvable before generation)
20.09.2012 09:09:49 (de.abg.reichert.joerg): status: Shape and Style are now realized with model inferrer instead of code generation (currently only in Spray juni) so the example project integration may continue
08.10.2012 21:07:35 (de.abg.reichert.joerg): with work around described in mail: http://groups.google.com/group/spray-dev/msg/748188e9cef8b4c6 LWC 2012 and BPMN example project are also included now. Fowler DSL example project have to be revised anyway.
17.04.2013 22:08:08 (de.abg.reichert.joerg):
- stakeholder: Spray user
- keywords: Type: Task, Priority: High
- status: IN_PROGRESS

## issue0147
Document JaCoCo setup in Spray developer documentation
08.07.2012 17:37:00 (de.abg.reichert.joerg): The Spray build supports code coverage measurement via JaCoCo. This should be documented in the Spray developer guide.
- stakeholder: Spray user
- keywords: Type: Task, Priority: Low
- status: OPEN

## issue0148
Document Sonar in Spray developer guide
08.07.2012 17:40:01 (de.abg.reichert.joerg): The Spray build supports metrics collection via Sonar. This should be documented in the Spray developer guide. The guide should also cover which components are to exclude from investigation (how to exclude the generated code parts). Further the usage of Sonar (web interface as well as Eclipse plug-in) should be shown.
- stakeholder: Spray user
- keywords: Type: Task, Priority: Low
- status: OPEN

## issue0149
Investigate out of memory in xtend-maven-plugin in local build
08.07.2012 17:46:08 (de.abg.reichert.joerg): When I build Spray modules-default locally I get an out of memory exception when the build executes the xtend-maven-plugin in org.eclipselabs.spray.xtext. When executed sole org.eclipselabs.spray.xtext builds succesfully. Also the CI server is able to execute the hole build. But locally even with memory settings set in MAVEN_OPTS I am not able to complete the modules-default build.
01.09.2012 10:02:51 (de.abg.reichert.joerg): Had to set MAVEN_OPTS="-Xms256m -Xmx1024m -XX:MaxPermSize=512m -XX:PermSize=512m" in the Windows environment to fix the problem as setting locally in Windows Powershell had no effect.
- stakeholder: Spray user
- keywords: Type: Task, Priority: Low
- status: DONE

## issue0150
Improve performance of domain model completion in Spray DSL
08.07.2012 17:51:20 (de.abg.reichert.joerg): To enable references to domain model elements from EMF models found in other workspace projects in every completion the complete workspace in scanned again.
There should be added some clever caching, e.g. only calculate EMF models when scoping the packages.
Also the scope of the domain model classes should be reduced: Only classes from EPackages whose import is declared explicitly in the Spray DSL should be proposed.
20.09.2012 09:05:12 (de.abg.reichert.joerg): Cache is enabled in latest Spray Juno build:
https://spray.ci.cloudbees.com/job/spray-assembly-build/59/artifact/releng/org.eclipselabs.spray.updatesite/target/repository/#
Still have to applied to Indigo branch
24.09.2012 18:39:18 (de.abg.reichert.joerg): When changing an existing domain model project the Scoping still uses the cached values instead invalidating the cache, cf. http://groups.google.com/group/spray-dev/browse_thread/thread/1e7d44e7b4db4b32
24.09.2012 18:40:07 (de.abg.reichert.joerg): a workaround for the cache rebuild problem is to restart Eclipse
08.10.2012 21:11:33 (de.abg.reichert.joerg): the (re-)calculation of available and accessible EPackages is triggered if referenced Java projects of the current Java project are dirty (the current project is excluded as when the generator runs, this project is too often dirty).
14.10.2012 22:33:29 (de.abg.reichert.joerg): if any problems, please reopen.
- stakeholder: Spray user
- keywords: Type: Enhancement, Priority: Medium
- status: DONE

## issue0151
Comments in Shape and Style DSL are not colored like comments
08.07.2012 18:01:16 (de.abg.reichert.joerg): Comments in Java are colored green. Spray DSL also do this. Only Shape and Style DSL do not use this highlighting.
14.10.2012 22:26:26 (de.abg.reichert.joerg): Fixed at master and at Indigo branch.
- stakeholder: Spray user
- keywords: Type: Defect, Priority: Low
- status: DONE

## issue0152
A generated Spray projects in Juno still imports org.eclipse.xtext.xtend2.lib,
08.07.2012 18:04:49 (de.abg.reichert.joerg): in Juno there is no org.eclipse.xtext.xtend2.lib anymore.
01.09.2012 20:38:50 (de.abg.reichert.joerg):
- stakeholder: Spray user
- keywords: Type: Defect, Priority: Medium
- status: DONE

## issue0153
org.eclipselabs.spray.styles not included in generated MANIFEST.MF
08.07.2012 18:08:26 (de.abg.reichert.joerg): The generated MydiagramDefaultStyle.java includes following import:
import org.eclipselabs.spray.styles.generator.util.GradientUtilClass;
This import cannot be resolved as the plug-in org.eclipselabs.spray.styles is not included as dependency in the generated MANIFEST.MF.
01.09.2012 20:38:16 (de.abg.reichert.joerg):
- stakeholder: Spray user
- keywords: Type: Defect, Priority: Medium
- status: DONE

## issue0154
Empty compartment name for connection
08.07.2012 18:17:15 (de.abg.reichert.joerg): using following valid connection definition
class Association {
connection ( ) {
from source
to target
fromText text ( ) {
&quot;&quot;
}
toText text ( ) {
&quot;&quot;
}
connectionText text ( ) {
&quot;&quot;
}
}
behavior {
create into associations palette &quot;PaletteName&quot; askFor name
}
}
results in an empty compartment name (with hover you see that it exists).
01.09.2012 20:39:14 (de.abg.reichert.joerg):
- stakeholder: Spray user
- keywords: Type: Defect, Priority: Medium
- status: DONE

## issue0155
Prepare Spray 0.5 release
08.07.2012 18:20:59 (de.abg.reichert.joerg): We should make a release of the current state of Spray as Spray 0.5.
* refresh documentation (user, developer)
* fix tests
* Juno version
* Indigo version? (should a Indigo version maintained, what about branches, should the eclipse_juno branch switched to master, and the current master as eclipse_indigo?)
* what about a Spray product build
* other things.
- stakeholder: Spray user
- keywords: Type: Task, Priority: High
- status: OPEN

## issue0156
NPE at SprayScopeProvider.scope_Connection_from
01.09.2012 12:28:30 (de.abg.reichert.joerg): <b>What steps will reproduce the problem?</b>
Editing the connection definition inside the Spray DSL
<b>What is the expected output? What do you see instead?</b>
!MESSAGE An internal error occurred during: &quot;Xtext validation&quot;.
!STACK 0
org.eclipse.emf.common.util.WrappedException: org.eclipse.emf.common.util.WrappedException: java.lang.NullPointerException
at org.eclipse.xtext.util.OnChangeEvictingCache.execWithoutCacheClear(OnChangeEvictingCache.java:123)
at org.eclipse.xtext.xbase.resource.XbaseResource.getEObject(XbaseResource.java:225)
at org.eclipse.xtext.linking.lazy.LazyLinkingResource.resolveLazyCrossReference(LazyLinkingResource.java:143)
at org.eclipse.xtext.linking.lazy.LazyLinkingResource.resolveLazyCrossReferences(LazyLinkingResource.java:104)
at org.eclipse.xtext.EcoreUtil2.resolveLazyCrossReferences(EcoreUtil2.java:491)
at org.eclipse.xtext.validation.ResourceValidatorImpl.resolveProxies(ResourceValidatorImpl.java:127)
at org.eclipse.xtext.validation.ResourceValidatorImpl.validate(ResourceValidatorImpl.java:62)
at org.eclipse.xtext.ui.editor.validation.ValidationJob$1.exec(ValidationJob.java:79)
at org.eclipse.xtext.ui.editor.validation.ValidationJob$1.exec(ValidationJob.java:1)
at org.eclipse.xtext.util.concurrent.AbstractReadWriteAcces.readOnly(AbstractReadWriteAcces.java:32)
at org.eclipse.xtext.ui.editor.model.XtextDocument.readOnly(XtextDocument.java:78)
at org.eclipse.xtext.ui.editor.validation.ValidationJob.createIssues(ValidationJob.java:75)
at org.eclipse.xtext.ui.editor.validation.ValidationJob.run(ValidationJob.java:64)
at org.eclipse.core.internal.jobs.Worker.run(Worker.java:54)
Caused by: org.eclipse.emf.common.util.WrappedException: java.lang.NullPointerException
at org.eclipse.xtext.linking.lazy.LazyLinkingResource.getEObject(LazyLinkingResource.java:209)
at org.eclipse.xtext.xbase.resource.XbaseResource.access$0(XbaseResource.java:1)
at org.eclipse.xtext.xbase.resource.XbaseResource$2.exec(XbaseResource.java:227)
at org.eclipse.xtext.xbase.resource.XbaseResource$2.exec(XbaseResource.java:1)
at org.eclipse.xtext.util.OnChangeEvictingCache.execWithoutCacheClear(OnChangeEvictingCache.java:121)
... 13 more
Caused by: java.lang.NullPointerException
at org.eclipselabs.spray.xtext.scoping.SprayScopeProvider.scope_Connection_from(SprayScopeProvider.java:254)
at org.eclipselabs.spray.xtext.scoping.SprayScopeProvider.getScope(SprayScopeProvider.java:112)
at org.eclipse.xtext.xbase.linking.XbaseLinkingScopeProvider.getScope(XbaseLinkingScopeProvider.java:42)
at org.eclipse.xtext.linking.impl.DefaultLinkingService.getScope(DefaultLinkingService.java:59)
at org.eclipse.xtext.linking.impl.DefaultLinkingService.getLinkedObjects(DefaultLinkingService.java:119)
at org.eclipse.xtext.linking.lazy.LazyLinkingResource.getEObject(LazyLinkingResource.java:175)
... 17 more
Experienced with Spray Indigo, may apply to Spray Juno , too
01.09.2012 20:39:01 (de.abg.reichert.joerg):
- stakeholder: Spray user
- keywords: Type: Defect, Priority: Medium
- status: DONE

## issue0157
A bulk of PackageNotFoundExceptions after each Scope call
02.09.2012 10:54:10 (de.abg.reichert.joerg): Very likely by the brute force fix of http://code.google.com/a/eclipselabs.org/p/spray/issues/detail?id=127 there now occurs the following exceptions on the development Eclipse console when starting Spray from sources in a runtime workspace. With an installed Spray there are no such stack traces in the log file (that does mean that these exceptions occur there, too). In the source started Spray this execptions causes high reaction times, though.
org.eclipse.emf.ecore.resource.impl.ResourceSetImpl$1DiagnosticWrappedException: org.eclipse.emf.ecore.xmi.PackageNotFoundException: Package with uri 'http://www.eclipse.org/uml2/2.2.0/GenModel' not found. (platform:/plugin/org.eclipse.ocl/model/OCL.genmodel, 12, 75)
at org.eclipse.emf.ecore.resource.impl.ResourceSetImpl.handleDemandLoadException(ResourceSetImpl.java:319)
at org.eclipse.emf.ecore.resource.impl.ResourceSetImpl.demandLoadHelper(ResourceSetImpl.java:278)
at org.eclipse.emf.ecore.resource.impl.ResourceSetImpl.getResource(ResourceSetImpl.java:406)
at org.eclipselabs.spray.xtext.scoping.PackageSelector.getGenPackage(PackageSelector.java:219)
at org.eclipselabs.spray.xtext.scoping.PackageSelector.getGenPackage(PackageSelector.java:207)
at org.eclipselabs.spray.xtext.scoping.PackageSelector.filterAccessibleEPackages(PackageSelector.java:191)
at org.eclipselabs.spray.xtext.scoping.PackageSelector.getFilteredEPackages(PackageSelector.java:51)
at org.eclipselabs.spray.xtext.scoping.SprayScopeProvider.getImportedPackages(SprayScopeProvider.java:507)
at org.eclipselabs.spray.xtext.scoping.SprayScopeProvider.scopeEClasses(SprayScopeProvider.java:498)
at org.eclipselabs.spray.xtext.scoping.SprayScopeProvider.scope_MetaClass_Type(SprayScopeProvider.java:472)
at org.eclipselabs.spray.xtext.scoping.SprayScopeProvider.getScope(SprayScopeProvider.java:106)
at org.eclipse.xtext.xbase.linking.XbaseLinkingScopeProvider.getScope(XbaseLinkingScopeProvider.java:42)
at org.eclipse.xtext.linking.impl.DefaultLinkingService.getScope(DefaultLinkingService.java:59)
at org.eclipse.xtext.linking.impl.DefaultLinkingService.getLinkedObjects(DefaultLinkingService.java:119)
at org.eclipse.xtext.linking.lazy.LazyLinkingResource.getEObject(LazyLinkingResource.java:179)
at org.eclipse.xtext.xbase.resource.XbaseResource.access$0(XbaseResource.java:1)
at org.eclipse.xtext.xbase.resource.XbaseResource$2.exec(XbaseResource.java:239)
at org.eclipse.xtext.xbase.resource.XbaseResource$2.exec(XbaseResource.java:1)
at org.eclipse.xtext.util.OnChangeEvictingCache.execWithoutCacheClear(OnChangeEvictingCache.java:124)
at org.eclipse.xtext.xbase.resource.XbaseResource.getEObject(XbaseResource.java:237)
at org.eclipse.emf.ecore.resource.impl.ResourceSetImpl.getEObject(ResourceSetImpl.java:223)
at org.eclipse.emf.ecore.util.EcoreUtil.resolve(EcoreUtil.java:197)
at org.eclipse.emf.ecore.util.EcoreUtil.resolve(EcoreUtil.java:257)
at org.eclipse.emf.ecore.impl.BasicEObjectImpl.eResolveProxy(BasicEObjectImpl.java:1473)
at org.eclipselabs.spray.mm.spray.impl.MetaClassImpl.getType(MetaClassImpl.java:584)
at org.eclipselabs.spray.xtext.jvmmodel.SprayJvmModelInferrer._infer(SprayJvmModelInferrer.java:51)
at org.eclipselabs.spray.xtext.jvmmodel.SprayJvmModelInferrer.infer(SprayJvmModelInferrer.java:123)
at org.eclipse.xtext.xbase.jvmmodel.AbstractModelInferrer._infer(AbstractModelInferrer.java:69)
at org.eclipselabs.spray.xtext.jvmmodel.SprayJvmModelInferrer.infer(SprayJvmModelInferrer.java:126)
at org.eclipse.xtext.xbase.jvmmodel.JvmModelAssociator.installDerivedState(JvmModelAssociator.java:231)
at org.eclipse.xtext.resource.DerivedStateAwareResource.installDerivedState(DerivedStateAwareResource.java:125)
at org.eclipse.xtext.resource.DerivedStateAwareResource.getContents(DerivedStateAwareResource.java:48)
at org.eclipse.emf.ecore.util.EcoreUtil.getAllContents(EcoreUtil.java:1121)
at org.eclipse.xtext.linking.lazy.LazyLinkingResource.resolveLazyCrossReferences(LazyLinkingResource.java:97)
at org.eclipse.xtext.EcoreUtil2.resolveLazyCrossReferences(EcoreUtil2.java:497)
at org.eclipse.xtext.builder.clustering.ClusteringBuilderState.doUpdate(ClusteringBuilderState.java:204)
at org.eclipse.xtext.builder.builderState.AbstractBuilderState.update(AbstractBuilderState.java:105)
at org.eclipse.xtext.builder.impl.XtextBuilder.doBuild(XtextBuilder.java:159)
at org.eclipse.xtext.builder.impl.XtextBuilder.incrementalBuild(XtextBuilder.java:141)
at org.eclipse.xtext.builder.impl.XtextBuilder.build(XtextBuilder.java:91)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:239)
at org.eclipse.core.internal.events.BuildManager$1.run(BuildManager.java:292)
at org.eclipse.core.runtime.SafeRunner.run(SafeRunner.java:42)
at org.eclipse.core.internal.events.BuildManager.basicBuild(BuildManager.java:295)
at org.eclipse.core.internal.events.BuildManager.basicBuildLoop(BuildManager.java:351)
at org.eclipse.core.internal.events.BuildManager.build(BuildManager.java:374)
at org.eclipse.core.internal.events.AutoBuildJob.doBuild(AutoBuildJob.java:143)
at org.eclipse.core.internal.events.AutoBuildJob.run(AutoBuildJob.java:241)
at org.eclipse.core.internal.jobs.Worker.run(Worker.java:54)
Caused by: org.eclipse.emf.ecore.xmi.PackageNotFoundException: Package with uri 'http://www.eclipse.org/uml2/2.2.0/GenModel' not found. (platform:/plugin/org.eclipse.ocl/model/OCL.genmodel, 12, 75)
at org.eclipse.emf.ecore.xmi.impl.XMLHandler.getPackageForURI(XMLHandler.java:2585)
at org.eclipse.emf.ecore.xmi.impl.XMLHandler.getFactoryForPrefix(XMLHandler.java:2416)
at org.eclipse.emf.ecore.xmi.impl.XMLHandler.createObjectByType(XMLHandler.java:1293)
at org.eclipse.emf.ecore.xmi.impl.XMLHandler.createTopObject(XMLHandler.java:1462)
at org.eclipse.emf.ecore.xmi.impl.XMLHandler.processElement(XMLHandler.java:1013)
at org.eclipse.emf.ecore.xmi.impl.XMIHandler.processElement(XMIHandler.java:77)
at org.eclipse.emf.ecore.xmi.impl.XMLHandler.startElement(XMLHandler.java:995)
at org.eclipse.emf.ecore.xmi.impl.XMLHandler.startElement(XMLHandler.java:706)
at org.eclipse.emf.ecore.xmi.impl.XMIHandler.startElement(XMIHandler.java:163)
at com.sun.org.apache.xerces.internal.parsers.AbstractSAXParser.startElement(AbstractSAXParser.java:506)
at com.sun.org.apache.xerces.internal.impl.dtd.XMLDTDValidator.startElement(XMLDTDValidator.java:745)
at com.sun.org.apache.xerces.internal.impl.XMLDocumentFragmentScannerImpl.scanStartElement(XMLDocumentFragmentScannerImpl.java:1322)
at com.sun.org.apache.xerces.internal.impl.XMLDocumentScannerImpl$ContentDriver.scanRootElementHook(XMLDocumentScannerImpl.java:1275)
at com.sun.org.apache.xerces.internal.impl.XMLDocumentFragmentScannerImpl$FragmentContentDriver.next(XMLDocumentFragmentScannerImpl.java:3063)
at com.sun.org.apache.xerces.internal.impl.XMLDocumentScannerImpl$PrologDriver.next(XMLDocumentScannerImpl.java:881)
at com.sun.org.apache.xerces.internal.impl.XMLDocumentScannerImpl.next(XMLDocumentScannerImpl.java:607)
at com.sun.org.apache.xerces.internal.impl.XMLDocumentFragmentScannerImpl.scanDocument(XMLDocumentFragmentScannerImpl.java:488)
at com.sun.org.apache.xerces.internal.parsers.XML11Configuration.parse(XML11Configuration.java:835)
at com.sun.org.apache.xerces.internal.parsers.XML11Configuration.parse(XML11Configuration.java:764)
at com.sun.org.apache.xerces.internal.parsers.XMLParser.parse(XMLParser.java:123)
at com.sun.org.apache.xerces.internal.parsers.AbstractSAXParser.parse(AbstractSAXParser.java:1210)
at com.sun.org.apache.xerces.internal.jaxp.SAXParserImpl$JAXPSAXParser.parse(SAXParserImpl.java:568)
at com.sun.org.apache.xerces.internal.jaxp.SAXParserImpl.parse(SAXParserImpl.java:302)
at org.eclipse.emf.ecore.xmi.impl.XMLLoadImpl.load(XMLLoadImpl.java:175)
at org.eclipse.emf.ecore.xmi.impl.XMLResourceImpl.doLoad(XMLResourceImpl.java:240)
at org.eclipse.emf.ecore.resource.impl.ResourceImpl.load(ResourceImpl.java:1505)
at org.eclipse.emf.ecore.resource.impl.ResourceImpl.load(ResourceImpl.java:1284)
at org.eclipse.emf.ecore.resource.impl.ResourceSetImpl.demandLoad(ResourceSetImpl.java:259)
at org.eclipse.emf.ecore.resource.impl.ResourceSetImpl.demandLoadHelper(ResourceSetImpl.java:274)
... 50 more
20.09.2012 09:08:01 (de.abg.reichert.joerg): in the latest Spray Juno build (https://spray.ci.cloudbees.com/job/spray-assembly-build/59/artifact/releng/org.eclipselabs.spray.updatesite/target/repository/#) this have been resolved by caching (issue #150) and printing a smaller error message
Still have to be applied to the Spray indigo branch as well
10.10.2012 20:17:01 (de.abg.reichert.joerg): fixed also at indigo branch
- stakeholder: Spray user
- keywords: Type: Defect, Priority: Medium
- status: DONE

## issue0158
Exception at save of diagram file edited with generated Graphiti editor
02.09.2012 10:56:58 (de.abg.reichert.joerg): <b>What steps will reproduce the problem?</b>
1. Create simple diagram definition for the busmod mm
2. Start Spray from sources, create a new diagram and try to save the diagram file
!ENTRY org.eclipse.graphiti.ui 4 0 2012-09-02 10:18:08.232
!MESSAGE The following resources could not be saved:
URI: platform:/resource/Neu/src/my.mydsl, cause:
java.lang.RuntimeException: The context 'Model' is not valid for type 'BusinessDomainModel'
Recommended contexts for type 'BusinessDomainModel':
The context 'Model' is valid for types: Model, null
Semantic Object: BusinessDomainModel''
at org.eclipse.xtext.serializer.diagnostic.ISerializationDiagnostic$ExceptionThrowingAcceptor.accept(ISerializationDiagnostic.java:70)
at org.xtext.example.mydsl.serializer.AbstractMyDslSemanticSequencer.createSequence(AbstractMyDslSemanticSequencer.java:62)
at org.eclipse.xtext.serializer.impl.Serializer.serialize(Serializer.java:84)
at org.eclipse.xtext.serializer.impl.Serializer.serialize(Serializer.java:103)
at org.eclipse.xtext.serializer.impl.Serializer.serialize(Serializer.java:125)
at org.eclipse.xtext.resource.XtextResource.doSave(XtextResource.java:313)
at org.eclipse.emf.ecore.resource.impl.ResourceImpl.save(ResourceImpl.java:1423)
at org.eclipse.emf.ecore.resource.impl.ResourceImpl.save(ResourceImpl.java:992)
at org.eclipse.graphiti.ui.internal.services.impl.EmfService$1$1.run(EmfService.java:250)
at org.eclipse.emf.transaction.impl.TransactionalEditingDomainImpl.runExclusive(TransactionalEditingDomainImpl.java:328)
at org.eclipse.graphiti.ui.internal.services.impl.EmfService$1.run(EmfService.java:261)
at org.eclipse.core.internal.resources.Workspace.run(Workspace.java:2344)
at org.eclipse.core.internal.resources.Workspace.run(Workspace.java:2326)
at org.eclipse.graphiti.ui.internal.services.impl.EmfService.save(EmfService.java:273)
at org.eclipse.graphiti.ui.internal.services.impl.EmfService.save(EmfService.java:211)
at org.eclipse.graphiti.ui.internal.editor.DiagramEditorBehavior$3.execute(DiagramEditorBehavior.java:500)
at org.eclipse.ui.actions.WorkspaceModifyOperation$1.run(WorkspaceModifyOperation.java:106)
at org.eclipse.core.internal.resources.Workspace.run(Workspace.java:2344)
at org.eclipse.ui.actions.WorkspaceModifyOperation.run(WorkspaceModifyOperation.java:118)
at org.eclipse.jface.operation.ModalContext$ModalContextThread.run(ModalContext.java:121)
!STACK 0
java.lang.RuntimeException
at org.eclipse.graphiti.ui.internal.services.impl.EmfService.save(EmfService.java:275)
at org.eclipse.graphiti.ui.internal.services.impl.EmfService.save(EmfService.java:211)
at org.eclipse.graphiti.ui.internal.editor.DiagramEditorBehavior$3.execute(DiagramEditorBehavior.java:500)
at org.eclipse.ui.actions.WorkspaceModifyOperation$1.run(WorkspaceModifyOperation.java:106)
at org.eclipse.core.internal.resources.Workspace.run(Workspace.java:2344)
at org.eclipse.ui.actions.WorkspaceModifyOperation.run(WorkspaceModifyOperation.java:118)
at org.eclipse.jface.operation.ModalContext$ModalContextThread.run(ModalContext.java:121)
19.11.2012 16:46:01 (joswarmer): Joerg, can you check whether this still is a problem ? I cannot reproduce it.
20.11.2012 19:53:52 (de.abg.reichert.joerg): With the current development version I cannot reproduce it, too,
20.11.2012 20:16:35 (joswarmer): Fine, let's close it.
- stakeholder: Spray user
- keywords: Type: Defect, Priority: Medium
- status: DONE

## issue0159
ClassCastException when creating new diagram shape
02.09.2012 10:59:21 (de.abg.reichert.joerg): import BusinessDomainDsl.*
diagram mydiagram for BusinessDomainModel
class BusinessClass icon &quot;ecore/EClass.gif&quot; {
shape org.eclipselabs.spray.shapes.RectangleShape {
name into businessClassText
}
behavior {
// Enable create feature for this class and add it to the palette &quot;Shapes&quot;
create into types palette &quot;Shapes&quot;;
}
}
shape RectangleShape style org.eclipselabs.spray.styles.Neu {
rectangle style org.eclipselabs.spray.styles.Neu {
position(x=0,y=0)
size(width=100,height=100)
style (background-color = org.eclipselabs.spray.styles.gradients.Neuer)
text {
position(x=5,y=5)
size(width=90,height=50)
style (background-color=yellow)
id = businessClassText
}
}
}
style MydiagramDefaultStyle {
description = &quot;The default style of the mydiagram diagram type.&quot;
// transparency = 0.95
background-color = org.eclipselabs.spray.styles.gradients.Neuer
// line-color = black
// line-style = solid
// line-width = 1
// font-color = black
// font-name = &quot;Tahoma&quot;
font-size = 12
// font-bold = yes
}
gradient Neuer {
area (color=blue, offset=0.0)
area (color=white, offset=1.0)
}
style Neu extends org.eclipselabs.spray.styles.MydiagramDefaultStyle {
background-color = green
}
!ENTRY org.eclipse.graphiti.ui 4 0 2012-09-02 10:21:05.675
!MESSAGE GFCommandStack.execute(Command) java.lang.ClassCastException: org.eclipse.emf.ecore.impl.EObjectImpl cannot be cast to BusinessDomainDsl.BusinessDomainModel
!STACK 0
java.lang.ClassCastException: org.eclipse.emf.ecore.impl.EObjectImpl cannot be cast to BusinessDomainDsl.BusinessDomainModel
at org.eclipselabs.spray.examples.mydiagram.diagram.MydiagramModelService.getModel(MydiagramModelService.java:46)
at org.eclipselabs.spray.examples.mydiagram.features.MydiagramCreateBusinessClassFeatureBase.createBusinessClass(MydiagramCreateBusinessClassFeatureBase.java:84)
at org.eclipselabs.spray.examples.mydiagram.features.MydiagramCreateBusinessClassFeatureBase.create(MydiagramCreateBusinessClassFeatureBase.java:58)
at org.eclipse.graphiti.features.impl.AbstractCreateFeature.execute(AbstractCreateFeature.java:100)
at org.eclipse.graphiti.internal.command.GenericFeatureCommandWithContext.execute(GenericFeatureCommandWithContext.java:64)
at org.eclipse.graphiti.internal.command.GFPreparableCommand.doExecute(GFPreparableCommand.java:37)
at org.eclipse.emf.transaction.RecordingCommand.execute(RecordingCommand.java:135)
at org.eclipse.graphiti.ui.internal.editor.GFWorkspaceCommandStackImpl.execute(GFWorkspaceCommandStackImpl.java:90)
at org.eclipse.emf.transaction.impl.AbstractTransactionalCommandStack.execute(AbstractTransactionalCommandStack.java:219)
at org.eclipse.graphiti.internal.command.CommandExec.executeCommand(CommandExec.java:75)
at org.eclipse.graphiti.ui.internal.command.CreateModelObjectCommand.execute(CreateModelObjectCommand.java:54)
at org.eclipse.graphiti.ui.internal.editor.EmfOnGefCommand.execute(EmfOnGefCommand.java:59)
at org.eclipse.graphiti.internal.command.GFPreparableCommand2.doExecute(GFPreparableCommand2.java:37)
at org.eclipse.emf.transaction.RecordingCommand.execute(RecordingCommand.java:135)
at org.eclipse.emf.workspace.EMFCommandOperation.doExecute(EMFCommandOperation.java:119)
at org.eclipse.emf.workspace.AbstractEMFOperation.execute(AbstractEMFOperation.java:150)
at org.eclipse.core.commands.operations.DefaultOperationHistory.execute(DefaultOperationHistory.java:513)
at org.eclipse.emf.workspace.impl.WorkspaceCommandStackImpl.doExecute(WorkspaceCommandStackImpl.java:208)
at org.eclipse.emf.transaction.impl.AbstractTransactionalCommandStack.execute(AbstractTransactionalCommandStack.java:165)
at org.eclipse.graphiti.ui.internal.editor.GFWorkspaceCommandStackImpl.execute(GFWorkspaceCommandStackImpl.java:71)
at org.eclipse.graphiti.ui.internal.editor.GFCommandStack.execute(GFCommandStack.java:124)
at org.eclipse.gef.tools.AbstractTool.executeCommand(AbstractTool.java:425)
at org.eclipse.gef.tools.AbstractTool.executeCurrentCommand(AbstractTool.java:438)
at org.eclipse.gef.tools.CreationTool.performCreation(CreationTool.java:269)
at org.eclipse.gef.tools.CreationTool.handleButtonUp(CreationTool.java:189)
at org.eclipse.gef.tools.AbstractTool.mouseUp(AbstractTool.java:1200)
at org.eclipse.gef.EditDomain.mouseUp(EditDomain.java:301)
at org.eclipse.gef.ui.parts.DomainEventDispatcher.dispatchMouseReleased(DomainEventDispatcher.java:380)
at org.eclipse.draw2d.LightweightSystem$EventHandler.mouseUp(LightweightSystem.java:548)
at org.eclipse.swt.widgets.TypedListener.handleEvent(TypedListener.java:219)
at org.eclipse.swt.widgets.EventTable.sendEvent(EventTable.java:84)
at org.eclipse.swt.widgets.Widget.sendEvent(Widget.java:1053)
at org.eclipse.swt.widgets.Display.runDeferredEvents(Display.java:4165)
at org.eclipse.swt.widgets.Display.readAndDispatch(Display.java:3754)
at org.eclipse.ui.internal.Workbench.runEventLoop(Workbench.java:2701)
at org.eclipse.ui.internal.Workbench.runUI(Workbench.java:2665)
at org.eclipse.ui.internal.Workbench.access$4(Workbench.java:2499)
at org.eclipse.ui.internal.Workbench$7.run(Workbench.java:679)
at org.eclipse.core.databinding.observable.Realm.runWithDefault(Realm.java:332)
at org.eclipse.ui.internal.Workbench.createAndRunWorkbench(Workbench.java:668)
at org.eclipse.ui.PlatformUI.createAndRunWorkbench(PlatformUI.java:149)
at org.eclipse.ui.internal.ide.application.IDEApplication.start(IDEApplication.java:123)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:344)
at org.eclipse.core.runtime.adaptor.EclipseStarter.run(EclipseStarter.java:179)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.equinox.launcher.Main.invokeFramework(Main.java:622)
at org.eclipse.equinox.launcher.Main.basicRun(Main.java:577)
at org.eclipse.equinox.launcher.Main.run(Main.java:1410)
at org.eclipse.equinox.launcher.Main.main(Main.java:1386)
19.11.2012 15:55:42 (joswarmer): This happens when you have an open diagram editor, close eclipse and open it again. The reference to the businessclassmodel is an EObject which seems a proxy to the real object and therefore the cast goes wrong. Don't know why this isn't simply resolved.
19.11.2012 16:30:02 (joswarmer): Tried to resolve the proxy using EcoreUtil(2).resolve(object, resourceset), but this does not make any difference.
19.11.2012 16:44:18 (joswarmer): Proxy resolved by getting the resource set and finding the object through its URI.
- stakeholder: Spray user
- keywords: Type: Defect, Priority: Medium
- status: DONE

## issue0160
Referencing a style definition has no effect
02.09.2012 11:06:15 (de.abg.reichert.joerg): <b>What steps will reproduce the problem?</b>
1. Define a style in the style DSL file
2. Reference the style in Spray DSL or Shape DSL
No effect:
* at diagram: diagram mydiagram for BusinessDomainModel style org.eclipselabs.spray.styles.MydiagramDefaultStyle
* at metaclass: class BusinessClass icon &quot;ecore/EClass.gif&quot; style org.eclipselabs.spray.styles.MydiagramDefaultStyle
* at shape: shape RectangleShape style org.eclipselabs.spray.styles.Neu
* at figure: rectangle style org.eclipselabs.spray.styles.Neu
Where it works:
* gradient reference in style attribute inside figure definition:
rectangle style org.eclipselabs.spray.styles.Neu {
...
style (background-color = org.eclipselabs.spray.styles.gradients.Neuer)
...
}
12.11.2012 16:25:20 (joswarmer): I have fixed all the font style properties (font-color, font-size, font-bold, font-italic, font-name). The generated code did set the Graphiti Style, but it seems the Font has to be set seperately. Might be a bug in Graphiti.
12.11.2012 17:09:48 (joswarmer): With some changes it now works for all style attributes except:
line-width, line-style and transparancy.
I did not yet test the gradients, but they seem to work.
12.11.2012 17:46:12 (joswarmer): Fixed line-wdth and line-style, transparancy does not seem to work at all.
12.11.2012 17:58:27 (joswarmer):
19.11.2012 13:45:23 (joswarmer): Fixed
- stakeholder: Spray user
- keywords: Type: Defect, Priority: High
- status: DONE

## issue0161
Link referenced shapes and styles definition not only to the generated Java file
02.09.2012 11:10:43 (de.abg.reichert.joerg): Provide user with selection whether to navigate to the generated Java file or to the corresponding DSL model element when clicking on a style resp. shape reference in the DSL editor. Currently it is always linked to the Java file.
10.10.2012 20:14:18 (de.abg.reichert.joerg):
- stakeholder: Spray user
- keywords: Type: Enhancement, Priority: Medium
- status: DONE

## issue0162
Propose gradient definition also at style attribute within shape definition
02.09.2012 11:13:28 (de.abg.reichert.joerg): At ...
rectangle style org.eclipselabs.spray.styles.Neu {
style (background-color = ...)
}
no existing gradient definition is proposed.
This currently works only inside the style DSL:
style MydiagramDefaultStyle {
background-color = org.eclipselabs.spray.styles.gradients.Neuer
}
02.09.2012 11:14:10 (de.abg.reichert.joerg): Writing the org.eclipselabs.spray.styles.gradients.Neuer manually at style (background-color = ... ) works.
04.12.2012 20:22:38 (de.abg.reichert.joerg): This issue was closed by revision 97e8cd8be5e1.
- stakeholder: Spray user
- keywords: Type: Defect, Priority: Low
- status: DONE

## issue0163
Better auto completion support in Shape and Style DSL
02.09.2012 11:19:47 (de.abg.reichert.joerg): elements in Style and Shape DSL are defined with the common pattern
[element-name] ([attribute1-name]=[attribute1-value],[attribute2-name]=[attribute2-value])
When typing in the editor the [element-name] is proposed but after it nothing is proposed. Same applies after the attribute1-name: no equal sign is proposed.
Either the the brackets should be proposed or better for each element that should exist an DSL template proposal that proposes the structure above.
08.11.2012 22:44:50 (de.abg.reichert.joerg): This issue was closed by revision e8fac6f376e5.
- stakeholder: Spray user
- keywords: Type: Enhancement, Priority: Medium
- status: DONE

## issue0164
Sort / prioritize elements in proposals
02.09.2012 12:11:43 (de.abg.reichert.joerg): When proposing EMF domain model elements inside the Spray DSL, elements contained in the already imported packages should be shown first. Also all elements should be sorted by package name and then element name.
Same applies to Shape and Style DSL. The in the current file available Shapes and Styles should be proposed first.
08.10.2012 21:12:29 (de.abg.reichert.joerg): Realized on Juno branch, see also mail: http://groups.google.com/group/spray-dev/msg/748188e9cef8b4c6
10.10.2012 19:22:48 (de.abg.reichert.joerg): migrated to indigo branch as well
- stakeholder: Spray user
- keywords: Type: Enhancement, Priority: Low
- status: DONE

## issue0165
Write a concept / overview of all scenarios creating diagram elements
02.09.2012 12:26:16 (de.abg.reichert.joerg): Currently there are quite a lot of restrictions in building up an domain model by creation of diagram elements. It should be documented inside the developer guide or in a wiki page, which creation scenarios are thinkable and whose of them are already support resp. what have to be done in Spray to enable the not yet supported scenarios.
Some examples:
* handling of containment and non-containment relationships in the domain meta model
* handling of recursion in the domain meta model
* handling of the scenario, where multiple diagram elements maps to one domain model element / feature
* handling of the scenario, where one diagram element maps to multiple domain model elements / features
* handling of the scenario, where the existence / appearance of a diagram element depends on value of domain model features
* handling of the scenario, where the existence / appearance of a diagram element depends on the existence of a certain structure in the domain model
* handling of the scenario, where the a domain model element appears for better visibility multiple times in a diagram (example: level that appears in multiple hierarchies)
* handling of the scenario, where a containment relationship in the domain model is depicted as nested shapes in a diagram
* handling of the scenario, where a containment relationship in the domain model is depicted by (styled) connection lines between diagram elements
* other scenarios ...
- stakeholder: Spray user
- keywords: Type: Task, Priority: Medium
- status: OPEN

## issue0166
Write scoping and proposal tests
02.09.2012 12:28:20 (de.abg.reichert.joerg): use Xtext XPECT to define Scoping (and auto completion) tests
23.12.2012 09:52:56 (de.abg.reichert.joerg): started in style.tests
- stakeholder: Spray user
- keywords: Type: Task
- status: IN_PROGRESS

## issue0167
Figures on the same level are marked as one would exeed the dimensions of the other
02.09.2012 13:15:15 (de.abg.reichert.joerg): The following shape is marked with the warning: &quot;The height of all subelements is bigger than max_height of the shape.&quot;
shape MyShape {
rectangle {
position(x=0,y=0)
size(width=50,height=50)
}
ellipse {
position(x=50,y=50)
size(width=50,height=150)
}
}
As the both figures have no common parent there should be no restriction in width and height (in Graphiti code these both figures may contained within a invisible rectangle that would receive the max dimension derived by width, height and position of its contained figures).
Only in the following the construct the validation would be ok, as the ellipse is nested inside the rectangle and thus should not exceed the dimensions of its containing figure:
shape MyShape2 {
rectangle {
position(x=0,y=0)
size(width=50,height=50)
ellipse {
position(x=5,y=5)
size(width=50,height=50)
}
}
}
If you have a look at the org.eclipselabs.spray.shapes.validation.ShapeJavaValidator that works with global variables, you see how tricky the calculation of the validation is.
- stakeholder: Spray user
- keywords: Type: Defect, Priority: Medium
- status: OPEN

## issue0168
Enable definition of connection by given start and end element
02.09.2012 13:34:08 (de.abg.reichert.joerg): Currently there must exist a domain meta model element that can be mapped to a connection. This domain meta model element holds references to the start and the end element. But the more common case is, that there two elements that have uni- o bi-directional association to each other without such an extra third element.
In the DSL it should be possible, to write something like this:
classes Element1 alias e1, Element2 alias e2 {
connection ( )
{
from e1.element2Reference // this is the reference of type Element2
to e2.element1Reference // this is the reference of type Element1
}
}
In the example above there is a bi-directional association between Element1 and Element2 assumed. Note that there might be different association roles between Element1 and Element2 defined like Person.parents-&gt;Person*, Person.siblings-&gt;Person*
The following example shows the case when there is only a uni-directional relationship from Element2 to Element1, i.e. Element1 does not know that it is referenced by Element2:
classes Element1 alias e1, Element2 alias e2 {
connection ( )
{
from e1 // this is the reference of type Element2
to e2.element1Reference // this is the reference of type Element1
}
}
If there is only one relationship feature on each Element of the corresponding type the relationship feature may left off in the definition:
classes Element1 alias e1, Element2 alias e2 {
connection ( )
{
from e1 // this is the reference of type Element2
to e2 // this is the reference of type Element1
}
}
03.11.2012 19:22:15 (joswarmer): This is currently possible using:
class BusinessClass alias FullClass {
container ( fill=dark_green )
{
text ( ) { "<<"+eClass.name+">> " + name};
}
references {
superclass : connection( )
}
behavior {
create into types palette "Shapes" askFor name ;
}
The superclass is just an EReference in the domain model. I think it makes sense to define this inside the meta class in which the reference is defined, as is done here.
- stakeholder: Spray user
- keywords: Type: Enhancement, Priority: Medium
- status: OPEN

## issue0169
Enable creation of element that are not direct children of the model root
02.09.2012 13:43:48 (de.abg.reichert.joerg): Domain model:
A &lt;&gt;-ab- B
B &lt;&gt;-bc- D
Currently it is only possible to define
diagram aDiagram for A
class B {
...
behavior {
create into ab palette &quot;Elements&quot;;
}
}
but it is not possible yet to define
class C {
...
behavior {
create into ab.bd palette &quot;Elements&quot;;
}
}
(with ab.bd navigating from A to C over B, in the diagram the representation of C have to be nested into the representation of B).
03.11.2012 19:13:47 (joswarmer): The ab.cd is only clear when you know from which B you start when creating a C. So you need to drag the C on top of B to create it, but then it would logically be rendered inside the B shape. This is how it works with compartments now. Howe else would you know to which B to add C.
27.11.2012 10:37:24 (joswarmer): Children of other nodes (except root) can be created inside compartments of their parent node.
- stakeholder: Spray user
- keywords: Type: Enhancement, Priority: Medium
- status: OPEN

## issue0170
Catch NPEs in model inferrer code
20.09.2012 09:13:50 (de.abg.reichert.joerg): By switching the style and shape generator code to be part of the model inferrer, code generation / model inferring is triggered while editing (instead by saving), so when there is currently an invalid model this causes a lot of NPEs in the model inferrer code resulting in nasty error message pop ups in the Xtext editor. So this spots in the code have to handle all scenarios when a elements are not yet set.
10.10.2012 20:15:07 (de.abg.reichert.joerg): model inferer minimized, no longer relevant
- stakeholder: Spray user
- keywords: Type: Defect, Priority: Medium
- status: DONE

## issue0171
Provide trace model for shape and style DSL
20.09.2012 09:15:40 (de.abg.reichert.joerg): By switching style and shape DSL to use a model inferrer it would be nice to insert trace points in the model inferrer code to enable debugging between Shape DSL and generated Shape Java class resp. Style DSL and generated Style Java class.
10.10.2012 20:16:03 (de.abg.reichert.joerg):
- stakeholder: Spray user
- keywords: Type: Enhancement, Priority: Medium
- status: OPEN

## issue0172
Add dynamic compartments to Shape DSL
23.09.2012 17:14:54 (joswarmer): Currently all shapes defined in the shape DSl have fixeed sizes. Thus they do not support compartments that grow depending on their contents. Inthe main Spray DSL, this kind of compartments is supported for compartments containing text.
This dynamic compartment concept should be generalized (not just for text) and added to the shape DSL.
30.09.2012 21:09:02 (joswarmer):
10.11.2012 19:26:27 (joswarmer): Implementation done, need to adjust the documentation (open anither issue for this)
- stakeholder: Spray user
- keywords: Type: Task, Priority: High
- status: DONE

## issue0173
Fix documentation before 0.5 release
24.09.2012 18:36:05 (de.abg.reichert.joerg): in this issue all things should be collected that have to be fixed and adapted in the user and developer documentation to be aligned to the current state of version 0.5:
* new keyword 'custom' when defining behavior -&gt; adapt user documentation
* add hint for the current situation that using the Cloudbees URL to the repository fails with timeout the workaround would be to download the zip file of that repository and use this as local update site then
24.09.2012 18:45:46 (de.abg.reichert.joerg): * fix use of position(offset=1.0,distance=0,angle=0,active=false) as now invalid syntax, cf. http://groups.google.com/group/spray-users/msg/f965691dd5499fb7
12.11.2012 16:26:13 (joswarmer):
- stakeholder: Spray user
- keywords: Type: Task, Priority: Medium
- status: OPEN

## issue0174
Add wizard option to decide about one file or two file model variant
24.09.2012 18:42:51 (de.abg.reichert.joerg): When creating a new Spray project there should be an option to decide if the domain and graphical model should be stored in one resource or if they are stored separately in two files side by side, cf. http://groups.google.com/group/spray-users/browse_thread/thread/86c62d4a1f305eeb
03.11.2012 19:24:24 (joswarmer): In would like to reject this issue. Having the domain model stored in the same resource as the Graphiti model is nice for making a quick example, but these two things should in practice always be separated. I think it is bad design to combine them.
03.11.2012 19:40:49 (joswarmer):
- stakeholder: Spray user
- keywords: Type: Enhancement, Priority: Low
- status: DONE

## issue0175
Have a look at setDoneChanges(true) in CreateFeature of Connections
24.09.2012 18:50:13 (de.abg.reichert.joerg): cf. http://groups.google.com/group/spray-users/browse_thread/thread/29420bf9600d5b50
10.11.2012 12:18:48 (joswarmer): Removed this, don't see any problems with this solution.
10.11.2012 12:18:49 (joswarmer): Removed this, don't see any problems with this solution.
- stakeholder: Spray user
- keywords: Type: Defect, Priority: Medium
- status: DONE

## issue0176
Renable SVG generator after switch to model inferrer in Shape DSL
24.09.2012 18:55:54 (de.abg.reichert.joerg): After the switch to model inferrer in the Shape DSL the generator is not bound anymore. As far as I know and tested it is not possible to bind IGenerator as well as model inferrer at the same time (this would hinder the model inferrer to run) so it is currently not possible to add even only the SVG generator. (Maybe this issue is because of the fact that the IGenerator clears all sources in src-gen before running and by this all produced resources by the model inferrer are lost - so the solution would be to adapt the SVG generator to only clear all existing svg files).
08.10.2012 21:15:07 (de.abg.reichert.joerg): Fixed on Juno branch, the model inferer checks now, if there is already a JVMType for the given qualified name (so no over generation of the file generated by the common generator).
10.10.2012 19:23:08 (de.abg.reichert.joerg): migrated to indigo branch as well
- stakeholder: Spray user
- keywords: Type: Defect, Priority: Medium
- status: DONE

## issue0177
Enable linking to style and gradients under their simple name
24.09.2012 18:59:50 (de.abg.reichert.joerg): Gradient and styles are bound as JVMTypeReferences whose are exported under their full qualified name. Additionally there is bound an import aware scope provider, that put the packages of styles and shapes in scope, so the simple names should be sufficient). Unfortunately you have to make a shape DSL artifact dirty and the save it to resolve also referenced styles with only their simple name given. This should be fixed.
08.10.2012 21:15:39 (de.abg.reichert.joerg): enabled on Juno branch
10.10.2012 19:23:45 (de.abg.reichert.joerg): migrated to indigo branch as well
- stakeholder: Spray user
- keywords: Type: Defect, Priority: Medium
- status: DONE

## issue0178
Remove workaround for Duplicate JVMIdentifiableElement
24.09.2012 19:10:00 (de.abg.reichert.joerg): While inferring methods and their parameters I got a Duplicate JVMIdentifiableElement error for the created method parameters. This prevents the model inferrer to produce the Java code. I had to fix this be computing the parameter name by using the current model element name, although the parameter name is completely independent of the model element and its uniqueness should be scoped sufficiently by the inferred class.
Moreover as of modularization I have to generate a reassignment of the model element derived parameter name to the the actually intented parameter name, e.g.
parameters += element.toParameter(&quot;targetContainer&quot; + element.name.toFirstUpper, targetContainer)
parameters += element.toParameter(&quot;sprayStyle&quot; + element.name.toFirstUpper, sprayStyle)
body = [
var appendable = append('''// Create a ContainerShape for this Shape''').newLine
appendable = appendable.append(shapeGenerator.containerShapeType).append(''' targetContainer = targetContainer''' + element.name.toFirstUpper + ''';''').newLine
appendable = appendable.append(shapeGenerator.iSprayStyleType).append(''' sprayStyle = sprayStyle''' + element.name.toFirstUpper + ''';''').newLine
appendable = appendable.append(shapeGenerator.diagramType).append(''' diagram = peService.getDiagramForShape(targetContainer);''').newLine
cf. http://code.google.com/a/eclipselabs.org/p/spray/source/browse/plugins/org.eclipselabs.spray.shapes/src/org/eclipselabs/spray/shapes/jvmmodel/ShapeDefinitionTypeInferrer.xtend
01.10.2012 10:19:30 (de.abg.reichert.joerg): moved inferer code to branch:
http://code.google.com/a/eclipselabs.org/p/spray/source/browse/plugins/org.eclipselabs.spray.shapes/src/org/eclipselabs/spray/shapes/jvmmodel/ShapeDefinitionTypeInferrer.xtend?name=styles_shapes_inferer
10.10.2012 19:26:11 (de.abg.reichert.joerg): discontinued complete inferer migration in favor for combination of small inferer + common generator
- stakeholder: Spray user
- keywords: Type: Defect, Priority: Low
- status: DONE

## issue0179
Make Maven build work under Windows for projects using model inferrer
24.09.2012 19:11:36 (de.abg.reichert.joerg): I am currently not able to build Spray on my Windows 7 machine as it fails with the first project that uses model inferrer. At a Linux machine same build runs through without errors. I though first of a Maven version issue, but it occurs for Maven 3.0.3 as well as 3.0.4.
[INFO] --- xtend-maven-plugin:2.3.1:compile (default) @ org.eclipselabs.spray.styles ---
85126 [main] ERROR e.compiler.batch.XtendBatchCompiler -
ERROR: GradientTypeInferrer.xtend - D:\git\spray\plugins\org.eclipselabs.spray.styles\src\org\eclipselabs\spray\styles\
jvmmodel\GradientTypeInferrer.xtend
30: The method append is undefined for the type GradientTypeInferrer
85129 [main] ERROR e.compiler.batch.XtendBatchCompiler -
ERROR: GradientTypeInferrer.xtend - D:\git\spray\plugins\org.eclipselabs.spray.styles\src\org\eclipselabs\spray\styles\
jvmmodel\GradientTypeInferrer.xtend
30: The method append is undefined for the type GradientTypeInferrer
85131 [main] ERROR e.compiler.batch.XtendBatchCompiler -
ERROR: GradientTypeInferrer.xtend - D:\git\spray\plugins\org.eclipselabs.spray.styles\src\org\eclipselabs\spray\styles\
jvmmodel\GradientTypeInferrer.xtend
30: The method append is undefined for the type GradientTypeInferrer
85134 [main] ERROR e.compiler.batch.XtendBatchCompiler -
ERROR: GradientTypeInferrer.xtend - D:\git\spray\plugins\org.eclipselabs.spray.styles\src\org\eclipselabs\spray\styles\
jvmmodel\GradientTypeInferrer.xtend
31: The method append is undefined for the type GradientTypeInferrer
85137 [main] ERROR e.compiler.batch.XtendBatchCompiler -
ERROR: GradientTypeInferrer.xtend - D:\git\spray\plugins\org.eclipselabs.spray.styles\src\org\eclipselabs\spray\styles\
jvmmodel\GradientTypeInferrer.xtend
31: The method append is undefined for the type GradientTypeInferrer
85139 [main] ERROR e.compiler.batch.XtendBatchCompiler -
ERROR: GradientTypeInferrer.xtend - D:\git\spray\plugins\org.eclipselabs.spray.styles\src\org\eclipselabs\spray\styles\
jvmmodel\GradientTypeInferrer.xtend
31: The method newLine is undefined for the type GradientTypeInferrer
85142 [main] ERROR e.compiler.batch.XtendBatchCompiler -
ERROR: GradientTypeInferrer.xtend - D:\git\spray\plugins\org.eclipselabs.spray.styles\src\org\eclipselabs\spray\styles\
jvmmodel\GradientTypeInferrer.xtend
32: The method append is undefined for the type GradientTypeInferrer
85144 [main] ERROR e.compiler.batch.XtendBatchCompiler -
ERROR: GradientTypeInferrer.xtend - D:\git\spray\plugins\org.eclipselabs.spray.styles\src\org\eclipselabs\spray\styles\
jvmmodel\GradientTypeInferrer.xtend
32: The method append is undefined for the type GradientTypeInferrer
85146 [main] ERROR e.compiler.batch.XtendBatchCompiler -
ERROR: GradientTypeInferrer.xtend - D:\git\spray\plugins\org.eclipselabs.spray.styles\src\org\eclipselabs\spray\styles\
jvmmodel\GradientTypeInferrer.xtend
32: The method append is undefined for the type GradientTypeInferrer
85149 [main] ERROR e.compiler.batch.XtendBatchCompiler -
ERROR: GradientTypeInferrer.xtend - D:\git\spray\plugins\org.eclipselabs.spray.styles\src\org\eclipselabs\spray\styles\
jvmmodel\GradientTypeInferrer.xtend
32: The method append is undefined for the type GradientTypeInferrer
85151 [main] ERROR e.compiler.batch.XtendBatchCompiler -
ERROR: GradientTypeInferrer.xtend - D:\git\spray\plugins\org.eclipselabs.spray.styles\src\org\eclipselabs\spray\styles\
jvmmodel\GradientTypeInferrer.xtend
33: The method append is undefined for the type GradientTypeInferrer
85154 [main] ERROR e.compiler.batch.XtendBatchCompiler -
ERROR: GradientTypeInferrer.xtend - D:\git\spray\plugins\org.eclipselabs.spray.styles\src\org\eclipselabs\spray\styles\
jvmmodel\GradientTypeInferrer.xtend
33: The method newLine is undefined for the type GradientTypeInferrer
85156 [main] ERROR e.compiler.batch.XtendBatchCompiler -
ERROR: GradientTypeInferrer.xtend - D:\git\spray\plugins\org.eclipselabs.spray.styles\src\org\eclipselabs\spray\styles\
jvmmodel\GradientTypeInferrer.xtend
35: The method createColorAreas is undefined for the type GradientTypeInferrer
85158 [main] ERROR e.compiler.batch.XtendBatchCompiler -
ERROR: GradientTypeInferrer.xtend - D:\git\spray\plugins\org.eclipselabs.spray.styles\src\org\eclipselabs\spray\styles\
jvmmodel\GradientTypeInferrer.xtend
37: The method append is undefined for the type GradientTypeInferrer
85161 [main] ERROR e.compiler.batch.XtendBatchCompiler -
ERROR: StyleTypeInferrer.xtend - D:\git\spray\plugins\org.eclipselabs.spray.styles\src\org\eclipselabs\spray\styles\jvm
model\StyleTypeInferrer.xtend
41: The method append is undefined for the type StyleTypeInferrer
85163 [main] ERROR e.compiler.batch.XtendBatchCompiler -
ERROR: StyleTypeInferrer.xtend - D:\git\spray\plugins\org.eclipselabs.spray.styles\src\org\eclipselabs\spray\styles\jvm
model\StyleTypeInferrer.xtend
41: The method append is undefined for the type StyleTypeInferrer
85166 [main] ERROR e.compiler.batch.XtendBatchCompiler -
ERROR: StyleTypeInferrer.xtend - D:\git\spray\plugins\org.eclipselabs.spray.styles\src\org\eclipselabs\spray\styles\jvm
model\StyleTypeInferrer.xtend
41: The method append is undefined for the type StyleTypeInferrer
85168 [main] ERROR e.compiler.batch.XtendBatchCompiler -
ERROR: StyleTypeInferrer.xtend - D:\git\spray\plugins\org.eclipselabs.spray.styles\src\org\eclipselabs\spray\styles\jvm
model\StyleTypeInferrer.xtend
41: The method append is undefined for the type StyleTypeInferrer
85170 [main] ERROR e.compiler.batch.XtendBatchCompiler -
ERROR: StyleTypeInferrer.xtend - D:\git\spray\plugins\org.eclipselabs.spray.styles\src\org\eclipselabs\spray\styles\jvm
model\StyleTypeInferrer.xtend
41: The method newLine is undefined for the type StyleTypeInferrer
85172 [main] ERROR e.compiler.batch.XtendBatchCompiler -
ERROR: StyleTypeInferrer.xtend - D:\git\spray\plugins\org.eclipselabs.spray.styles\src\org\eclipselabs\spray\styles\jvm
model\StyleTypeInferrer.xtend
42: The method newLine is undefined for the type StyleTypeInferrer
85174 [main] ERROR e.compiler.batch.XtendBatchCompiler -
ERROR: StyleTypeInferrer.xtend - D:\git\spray\plugins\org.eclipselabs.spray.styles\src\org\eclipselabs\spray\styles\jvm
model\StyleTypeInferrer.xtend
43: The method append is undefined for the type StyleTypeInferrer
85177 [main] ERROR e.compiler.batch.XtendBatchCompiler -
ERROR: StyleTypeInferrer.xtend - D:\git\spray\plugins\org.eclipselabs.spray.styles\src\org\eclipselabs\spray\styles\jvm
model\StyleTypeInferrer.xtend
43: The method newLine is undefined for the type StyleTypeInferrer
85180 [main] ERROR e.compiler.batch.XtendBatchCompiler -
ERROR: StyleTypeInferrer.xtend - D:\git\spray\plugins\org.eclipselabs.spray.styles\src\org\eclipselabs\spray\styles\jvm
model\StyleTypeInferrer.xtend
44: The method append is undefined for the type StyleTypeInferrer
85182 [main] ERROR e.compiler.batch.XtendBatchCompiler -
ERROR: StyleTypeInferrer.xtend - D:\git\spray\plugins\org.eclipselabs.spray.styles\src\org\eclipselabs\spray\styles\jvm
model\StyleTypeInferrer.xtend
44: The method append is undefined for the type StyleTypeInferrer
85185 [main] ERROR e.compiler.batch.XtendBatchCompiler -
ERROR: StyleTypeInferrer.xtend - D:\git\spray\plugins\org.eclipselabs.spray.styles\src\org\eclipselabs\spray\styles\jvm
model\StyleTypeInferrer.xtend
44: The method newLine is undefined for the type StyleTypeInferrer
85187 [main] ERROR e.compiler.batch.XtendBatchCompiler -
ERROR: StyleTypeInferrer.xtend - D:\git\spray\plugins\org.eclipselabs.spray.styles\src\org\eclipselabs\spray\styles\jvm
model\StyleTypeInferrer.xtend
45: The method append is undefined for the type StyleTypeInferrer
85189 [main] ERROR e.compiler.batch.XtendBatchCompiler -
ERROR: StyleTypeInferrer.xtend - D:\git\spray\plugins\org.eclipselabs.spray.styles\src\org\eclipselabs\spray\styles\jvm
model\StyleTypeInferrer.xtend
45: The method newLine is undefined for the type StyleTypeInferrer
85191 [main] ERROR e.compiler.batch.XtendBatchCompiler -
ERROR: StyleTypeInferrer.xtend - D:\git\spray\plugins\org.eclipselabs.spray.styles\src\org\eclipselabs\spray\styles\jvm
model\StyleTypeInferrer.xtend
46: The method append is undefined for the type StyleTypeInferrer
85194 [main] ERROR e.compiler.batch.XtendBatchCompiler -
ERROR: StyleTypeInferrer.xtend - D:\git\spray\plugins\org.eclipselabs.spray.styles\src\org\eclipselabs\spray\styles\jvm
model\StyleTypeInferrer.xtend
46: The method newLine is undefined for the type StyleTypeInferrer
85196 [main] ERROR e.compiler.batch.XtendBatchCompiler -
ERROR: StyleTypeInferrer.xtend - D:\git\spray\plugins\org.eclipselabs.spray.styles\src\org\eclipselabs\spray\styles\jvm
model\StyleTypeInferrer.xtend
47: The method createLayout is undefined for the type StyleTypeInferrer
85198 [main] ERROR e.compiler.batch.XtendBatchCompiler -
ERROR: StyleTypeInferrer.xtend - D:\git\spray\plugins\org.eclipselabs.spray.styles\src\org\eclipselabs\spray\styles\jvm
model\StyleTypeInferrer.xtend
47: The method newLine is undefined for the type StyleTypeInferrer
85201 [main] ERROR e.compiler.batch.XtendBatchCompiler -
ERROR: StyleTypeInferrer.xtend - D:\git\spray\plugins\org.eclipselabs.spray.styles\src\org\eclipselabs\spray\styles\jvm
model\StyleTypeInferrer.xtend
48: The method append is undefined for the type StyleTypeInferrer
85203 [main] ERROR e.compiler.batch.XtendBatchCompiler -
ERROR: StyleTypeInferrer.xtend - D:\git\spray\plugins\org.eclipselabs.spray.styles\src\org\eclipselabs\spray\styles\jvm
model\StyleTypeInferrer.xtend
59: There is no context to infer the closure's argument types from. Consider typing the arguments or use the closures in
a more specific context.
85206 [main] ERROR e.compiler.batch.XtendBatchCompiler -
ERROR: StyleTypeInferrer.xtend - D:\git\spray\plugins\org.eclipselabs.spray.styles\src\org\eclipselabs\spray\styles\jvm
model\StyleTypeInferrer.xtend
59: Incompatible types. Expected org.eclipse.xtext.xbase.XExpression but was (null)=&gt;org.eclipse.xtext.xbase.compiler.ou
tput.ITreeAppendable
85209 [main] ERROR e.compiler.batch.XtendBatchCompiler -
ERROR: StyleTypeInferrer.xtend - D:\git\spray\plugins\org.eclipselabs.spray.styles\src\org\eclipselabs\spray\styles\jvm
model\StyleTypeInferrer.xtend
61: Incompatible types. Expected org.eclipse.xtext.xbase.compiler.output.ITreeAppendable but was org.eclipselabs.spray.s
tyles.styles.StyleLayout
85212 [main] ERROR e.compiler.batch.XtendBatchCompiler -
ERROR: StyleTypeInferrer.xtend - D:\git\spray\plugins\org.eclipselabs.spray.styles\src\org\eclipselabs\spray\styles\jvm
model\StyleTypeInferrer.xtend
68: There is no context to infer the closure's argument types from. Consider typing the arguments or use the closures in
a more specific context.
85215 [main] ERROR e.compiler.batch.XtendBatchCompiler -
ERROR: StyleTypeInferrer.xtend - D:\git\spray\plugins\org.eclipselabs.spray.styles\src\org\eclipselabs\spray\styles\jvm
model\StyleTypeInferrer.xtend
68: Incompatible types. Expected org.eclipse.xtext.xbase.XExpression but was (null)=&gt;org.eclipse.xtext.xbase.compiler.ou
tput.ITreeAppendable
85217 [main] ERROR e.compiler.batch.XtendBatchCompiler -
ERROR: StyleTypeInferrer.xtend - D:\git\spray\plugins\org.eclipselabs.spray.styles\src\org\eclipselabs\spray\styles\jvm
model\StyleTypeInferrer.xtend
70: Invalid number of arguments. Expected (ITreeAppendable, StyleLayout)
85220 [main] ERROR e.compiler.batch.XtendBatchCompiler -
ERROR: StyleTypeInferrer.xtend - D:\git\spray\plugins\org.eclipselabs.spray.styles\src\org\eclipselabs\spray\styles\jvm
model\StyleTypeInferrer.xtend
70: Incompatible types. Expected org.eclipse.xtext.xbase.compiler.output.ITreeAppendable but was org.eclipselabs.spray.s
tyles.styles.StyleLayout
85223 [main] WARN e.compiler.batch.XtendBatchCompiler -
WARNING: StyleGenerator.xtend - D:\git\spray\plugins\org.eclipselabs.spray.styles\src\org\eclipselabs\spray\style
s\generator\StyleGenerator.xtend
178: The method getStyle(ITreeAppendable, Style) from the type StyleGenerator is never used locally.
10.10.2012 19:27:20 (de.abg.reichert.joerg): as by simplifying inferer use this does not happen anymore
- stakeholder: Spray user
- keywords: Type: Defect, Priority: Medium
- status: DONE

## issue0180
IllegalArgumentException i DefaulktSprayStyle
01.10.2012 14:26:31 (joswarmer): When using only the DefaultSprayStyle, I get the following exception:
!ENTRY org.eclipse.graphiti.ui 4 0 2012-10-01 14:03:55.465
!MESSAGE GFCommandStack.execute(Command) java.lang.IllegalArgumentException: Object AdaptedGradientColoredAreas or its attributes must not be null or empty
!STACK 0
java.lang.IllegalArgumentException: Object AdaptedGradientColoredAreas or its attributes must not be null or empty
at org.eclipse.graphiti.services.impl.GaServiceImpl.setRenderingStyle(GaServiceImpl.java:1710)
at org.eclipselabs.spray.runtime.graphiti.styles.DefaultSprayStyle.findStyle(DefaultSprayStyle.java:99)
at org.eclipselabs.spray.runtime.graphiti.styles.DefaultSprayStyle.getStyle(DefaultSprayStyle.java:31)
at org.eclipselabs.spray.shapes.RectangleShape2.getShape(RectangleShape2.java:72)
at org.eclipselabs.spray.examples.mydiagram.features.MydiagramAddEnumerationFeatureBase.add(MydiagramAddEnumerationFeatureBase.java:65)
at org.eclipse.graphiti.internal.command.AddFeatureCommandWithContext.execute(AddFeatureCommandWithContext.java:76)
at org.eclipse.graphiti.ui.internal.command.GefCommandWrapper.execute(GefCommandWrapper.java:51)
at org.eclipse.graphiti.ui.internal.editor.EmfOnGefCommand.execute(EmfOnGefCommand.java:54)
at org.eclipse.graphiti.internal.command.GFPreparableCommand2.doExecute(GFPreparableCommand2.java:37)
at org.eclipse.emf.transaction.RecordingCommand.execute(RecordingCommand.java:135)
at org.eclipse.graphiti.ui.internal.editor.GFWorkspaceCommandStackImpl.execute(GFWorkspaceCommandStackImpl.java:102)
at org.eclipse.graphiti.ui.internal.editor.GFCommandStack.execute(GFCommandStack.java:124)
at org.eclipse.graphiti.ui.editor.DiagramEditor.executeFeature(DiagramEditor.java:1950)
at org.eclipse.graphiti.features.impl.AbstractFeatureProvider.addIfPossible(AbstractFeatureProvider.java:331)
at org.eclipse.graphiti.features.impl.AbstractFeature.addGraphicalRepresentation(AbstractFeature.java:109)
at org.eclipselabs.spray.examples.mydiagram.features.MydiagramCreateEnumerationFeatureBase.create(MydiagramCreateEnumerationFeatureBase.java:64)
at org.eclipse.graphiti.features.impl.AbstractCreateFeature.execute(AbstractCreateFeature.java:100)
01.10.2012 14:26:56 (joswarmer): On the latest master branch.
08.10.2012 21:17:53 (de.abg.reichert.joerg): fixed: do not call GaServiceImpl.setRenderingStyle when GaService is null
10.10.2012 19:24:18 (de.abg.reichert.joerg): migrated to indigo branch as well
- stakeholder: Spray user
- keywords: Type: Defect, Priority: Medium
- status: DONE

## issue0181
Fix coordinates for SVG generation
08.10.2012 19:44:19 (joswarmer): The coordinates for the SVG pictures are not correct. This is probably because of an error in the nested coordinate system.
14.10.2012 22:28:18 (de.abg.reichert.joerg): Fixed at master and at Indigo branch: max width and height calculation did not respect x resp. coordinates, the width and height inside the svg tag was not calculated.
- stakeholder: Spray user
- keywords: Type: Task
- status: DONE

## issue0182
Compartments can also be other shapoes than rectangles
08.10.2012 19:50:35 (joswarmer): Currently a compartment is a rectangle (hard-coded). Instead the user should be able to define any closed shape (rectangle, rounded-rectangle, ellipse, polygon) as a compartment. Need to add this option to the DSL and to the code generator
03.11.2012 19:06:39 (joswarmer): Added ellipse.
10.11.2012 19:33:17 (joswarmer): Added ellipse to be a compartment as well.
19.11.2012 12:32:08 (joswarmer):
19.11.2012 16:50:46 (joswarmer):
17.04.2013 10:58:29 (de.abg.reichert.joerg): Issue 257 has been merged into this issue.
- stakeholder: Spray user
- keywords: Type: Task, Priority: Medium
- status: READY

## issue0183
Nested compartments are selectable
08.10.2012 19:59:27 (joswarmer): <b>What steps will reproduce the problem?</b>
1. Create shape with nested compartment
2.Ensure compartment is as large as the main shape
3.Now you can only select the compartment, and not the main shape anymore.
<b>What is the expected output? What do you see instead?</b>
- The compartment should not be selectable at all
- You should always be able to select the main shape
Posted in Graphitit forum, because this seems to be a Graphitit problem.
10.10.2012 12:43:21 (joswarmer): Fixed by overriding ToolBehaviorProvider.getSelection()
- stakeholder: Spray user
- keywords: Type: Defect, Priority: Medium
- status: DONE

## issue0184
SVG-generation folder
10.10.2012 16:45:42 (fabio.filippelli): Currently the SVGs will be generated in the shapes package (where the shape classes are). I don't like it much, becuase this blow up this package a lot. Wouldn't it be better to generate this files into a specific folder as &quot;images/&quot;.
14.10.2012 22:32:40 (de.abg.reichert.joerg): Fixed at master and at Indigo branch: svgs are generated to [project]/shapepreviews/svg and pngs to shapepreviews/png when first hover is invoked in Xtext editor on shape element resp. shape reference. There you can now also provide a png for a Shape only available as Java implementation. This picture will then be shown when hovering over the JVM reference to the shape class.
- stakeholder: Spray user
- keywords: Type: Defect, Priority: Low, Component: Codegen
- status: DONE

## issue0185
Gradient, Style and Shape Generator should support Generation Gap Pattern
14.10.2012 14:22:37 (de.abg.reichert.joerg): The artifacts generated from the Spray DSL follow the Generation Gap Pattern, so that there is a base and a gap class generated for each artifact, where the Gap class may moved to src folder to adapt it with manually written code.
This should be true also for the artifacts derived from Gradient, Style and Shape definition.
23.12.2012 09:53:24 (de.abg.reichert.joerg):
03.03.2013 17:15:30 (de.abg.reichert.joerg): Started extracting the generators from Style and Shape DSL projects into separate projects. Current state can be found on branch "gengap4all".
16.04.2013 20:51:13 (de.abg.reichert.joerg): This issue was closed by revision 714349010e2d.
- stakeholder: Spray user
- keywords: Type: Task
- status: DONE

## issue0186
Gradient, Style and Shape generator should respect *.properties file entries
14.10.2012 14:25:57 (de.abg.reichert.joerg): When creating a new Spray project there is [DiagramName].properties file generated into the model folder that e.g. the names of the Java package in that the Gradient, Style and Shape artifacts should be generated. These properties are currently not respected by Gradient, Style and Shape generator.
14.10.2012 14:26:46 (de.abg.reichert.joerg):
27.11.2012 10:32:29 (joswarmer):
27.11.2012 10:36:06 (joswarmer): properties file is now named spray.properties.
- stakeholder: Spray user
- keywords: Type: Defect, Priority: Low
- status: DONE

## issue0187
Integrate Xtext builder participants of DSLs with each other
14.10.2012 15:19:49 (de.abg.reichert.joerg): Currently the builder participants / generators of the different DSLs do know nothing about each other. So a change e.g. in the Style DSL that has no effect to references to style definitions in other DSLs may break the Java code basis as the generated Style Java code may not be compatible to the other generated Java code that uses this code.
So it would be best practice to always trigger the generator for all DSL artifacts that are potentially affected by the change in a DSL artifact, e.g. the Shape generator is also invoked when a style has changed as a shape can reference a style.
scenarios:
1. *.style file changed
1.1 style file contains only style definitions
* (re-)generate the Java file for the style definition
* if a style name has changed (or even deleted) this makes all elements dirty that references this style (as the reference should be broken then):
* style definitions that have defined this style as super style
* shape and connection definitions that references this style
* mapping definitions in .spray files that references this style
* if the style references a gradient that has been not generated yet in Java this generation should be triggered within this build
* if the style references a super style that has been not generated yet in Java this generation should be triggered within this build
1.2 style file contains only gradient definitions
* (re-)generate the Java file for the gradient definition
* if a gradient name has changed (or even deleted) this makes all elements dirty that references this gradient (as the reference should be broken then):
* style definitions that references this gradient
1.3 style file contains gradient and style definitions
* apply first 1.2 and then 1.1 as styles may depend on existing Gradient Java files
2. *.shape file changed
* (re-)generate the Java file for the shape definition
* if a shape name has changed (or even deleted) this makes all elements dirty that references this shape (as the reference should be broken then):
* mapping definitions in .spray files that references this shape
* if the shape references a style that has been not generated yet in Java this generation should be triggered within this build
3. *.spray file changed
* (re-)generate the Java files derived from the mapping definitions (i.e. all Graphiti feature classes as well as some more Graphiti related classes)
* if in the Spray file a style is referenced that has been not generated yet in Java this generation should be triggered within this build
* if in the Spray file a shape is referenced that has been not generated yet in Java this generation should be triggered within this build
4. domain model changed
* this should make Spray files dirty that references elements from the domain model
5. Workspace start
* it should be checked if there already Java files generated for .spray, .shape and .style files contained in a project if not so, the generation should be triggered (so it is not necessary to make existing files dirty or call explicitly clear project to trigger the generation) - this check could be done e.g. in the Activator class
04.11.2012 17:51:20 (de.abg.reichert.joerg): Sometimes the spray generator (for the .spray model file) is running ten times in a row. It only seems to happen for the spray file in the business domain project.
It happens when either the spray file itself is saved, or a spray file of another project. There are no other changes done in any other file.
Spray generating for model platform:/resource/org.eclipselabs.spray.examples.mydiagram/model/mydiagram.style
Spray generating for model platform:/resource/org.eclipselabs.spray.examples.mydiagram/model/mydiagram.style
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
Spray generating for model platform:/resource/org.eclipselabs.spray.examples.mydiagram/model/mydiagram.style
Spray generating for model platform:/resource/org.eclipselabs.spray.examples.mydiagram/model/mydiagram.spray
Spray generating for model platform:/resource/org.eclipselabs.spray.examples.mydiagram/model/mydiagram.shape
04.11.2012 19:25:49 (joswarmer): The above number of generator step happens after saving the style model. As the style model itself uses the generated Jav style files, it can trigger itself in a loop. We should avoid that some way.
04.11.2012 19:38:49 (joswarmer): To avoid loops in style dependencies we should have an Xtext rule in the style grammar like:
Style:
{Style}
"style" name=ID ("extends" (superStyle=JvmTypeReference | superStyleFromDsl=[Style]) )? "{"
("description" "=" description=STRING)?
layout=StyleLayout
"}";
instead of:
Style:
{Style}
"style" name=ID ("extends" superStyle=JvmTypeReference)? "{"
("description" "=" description=STRING)?
layout=StyleLayout
"}";
That way a style can either refer to a style in the DSL or to a Java style.
- stakeholder: Spray user
- keywords: Type: Enhancement, Priority: Medium
- status: READY

## issue0188
SVG-Generator Bugs (Size and Compartments)
14.10.2012 23:39:32 (fabio.filippelli): There are still some issues regarding the SVG generator.
Issue 1. The SVG (and on hoover the PNG) pictures will be cutted on the right side. Please try to generate the attached shapes to reproduce this issue (&quot;issue1.shape&quot;).
Issue 2. While using nested shapes/compartments the SVG-file shows up two elements positionied on a wrong position. See attached file &quot;issue2.shape&quot;.
Regards
15.10.2012 05:17:19 (de.abg.reichert.joerg): Issue 1: Thought, that I have fixed this by given +5 extra each for height and width in svg tag
Issue 2: For nested shapes the position should be also fixed
I tracked this is in issue #181
But I will have look at it again if its really fixed.
16.10.2012 08:19:42 (de.abg.reichert.joerg): Ok, I found the mistakes:
* Issue 1 is related only to polygons, the width and height is now calculated correctly
* Issue 2: shapes uses some default offset, so that they do not start in (0,0), when using those shapes as nested shapes this default offset is now not applied anymore
16.10.2012 09:12:35 (joswarmer): Right, the shapes used to be a hierarchy of graphics algorithms, but has been changed to a hierarchy of of container shapes. Each subshape has coordinates relative to the parent shape. However, when there is an active cotainershape inside a non active containershape, Graphiti does not use the relative coordinates. For generating the shapes in the editor, I have a "fix" operation that fixes these coordinates. the same should be applied to the SVG generator.
18.11.2012 16:23:55 (de.abg.reichert.joerg): * fixed position calculation (absolute and container relative works now)
* added style interpretation (currently only directly annotated style
information)
* added connection decoration interpretation
* still missing:
* font attribute interpretation
* interpretation of text align
* interpretation of placing's radius and angle,
* referenced style interpretation
* gradients interpretation
* color interpretation based on numbers
- stakeholder: Spray user
- keywords: Type: Defect, Priority: Medium, Component: Codegen
- status: IN_PROGRESS

## issue0189
Using Container and Shape together
16.10.2012 13:43:07 (frb501@york.ac.uk): Hi,
I'm trying to use the Container object with a Shape.
Something like this:
container()
{
shape myDecoratingShape {}
text ( ) { &quot;&lt;&lt;&quot;+capabilityName+&quot;&gt;&gt;&quot; }
reference measurements attribute measurementName;
}
The problem is when I put a Shape (containing rectangles, etc...) inside a container and attempt to draw it,
all I get is a line.
I suppose what I really want to do is embed the container within the shape its self.
Is this possible and if so how do you go about doing it?
16.10.2012 19:41:11 (joswarmer): Shapes and containers cannot be used together at this moment. I am working on integrating the containers into the shape DSL to allow exactly what you want. See issue http://code.google.com/a/eclipselabs.org/p/spray/issues/detail?id=172.
12.11.2012 16:26:39 (joswarmer):
- stakeholder: Spray user
- keywords: Type: Enhancement, Priority: Medium
- status: READY

## issue0190
Define shape and style for anchors
19.10.2012 18:48:17 (joswarmer): Anchors currently are circles with light grey fill. It would ne nice to be able to use other shapes as anchors and to give them a style.
19.11.2012 12:31:39 (joswarmer):
19.11.2012 16:51:32 (joswarmer):
17.05.2013 17:02:39 (de.abg.reichert.joerg):
- stakeholder: Spray user
- keywords: Type: Enhancement, Priority: Low
- status: READY

## issue0191
Spray model editor gets weird eception if properties file does not exist
23.10.2012 19:22:16 (joswarmer): <b>What steps will reproduce the problem?</b>
1. Create a Spray project
2. Create a spray model file
3. DO not create a properties file, or at least one with a different namne from the spray mode3l
Try to open the spray model in the spray editor and you get an exception.
If you look good, halfway there is a SprayMultipage editor, trying to open a properties tab.
Java.lang.NullPointerException
at org.eclipse.ui.texteditor.MarkerRulerAction.getDocument(MarkerRulerAction.java:282)
at org.eclipse.ui.texteditor.MarkerRulerAction.update(MarkerRulerAction.java:194)
at org.eclipse.ui.texteditor.AbstractRulerActionDelegate.update(AbstractRulerActionDelegate.java:132)
at org.eclipse.ui.texteditor.AbstractRulerActionDelegate.setActiveEditor(AbstractRulerActionDelegate.java:89)
at org.eclipse.ui.internal.EditorPluginAction.editorChanged(EditorPluginAction.java:75)
at org.eclipse.ui.internal.EditorPluginAction.&lt;init&gt;(EditorPluginAction.java:34)
at org.eclipse.ui.internal.ActionDescriptor.createAction(ActionDescriptor.java:262)
at org.eclipse.ui.internal.ActionDescriptor.&lt;init&gt;(ActionDescriptor.java:176)
at org.eclipse.ui.internal.ViewerActionBuilder.createActionDescriptor(ViewerActionBuilder.java:53)
at org.eclipse.ui.internal.PluginActionBuilder.readElement(PluginActionBuilder.java:161)
at org.eclipse.ui.internal.ViewerActionBuilder.readElement(ViewerActionBuilder.java:88)
at org.eclipse.ui.internal.registry.RegistryReader.readElements(RegistryReader.java:144)
at org.eclipse.ui.internal.registry.RegistryReader.readElementChildren(RegistryReader.java:133)
at org.eclipse.ui.internal.PluginActionBuilder.readElement(PluginActionBuilder.java:144)
at org.eclipse.ui.internal.ViewerActionBuilder.readElement(ViewerActionBuilder.java:88)
at org.eclipse.ui.internal.registry.RegistryReader.readElements(RegistryReader.java:144)
at org.eclipse.ui.internal.registry.RegistryReader.readExtension(RegistryReader.java:155)
at org.eclipse.ui.internal.registry.RegistryReader.readRegistry(RegistryReader.java:176)
at org.eclipse.ui.internal.PluginActionBuilder.readContributions(PluginActionBuilder.java:115)
at org.eclipse.ui.internal.ViewerActionBuilder.readViewerContributions(ViewerActionBuilder.java:106)
at org.eclipse.ui.internal.PopupMenuExtender.readStaticActionsFor(PopupMenuExtender.java:524)
at org.eclipse.ui.internal.PopupMenuExtender.addMenuId(PopupMenuExtender.java:228)
at org.eclipse.ui.internal.PopupMenuExtender.&lt;init&gt;(PopupMenuExtender.java:148)
at org.eclipse.ui.internal.PartSite.registerContextMenu(PartSite.java:130)
at org.eclipse.ui.part.MultiPageEditorSite.registerContextMenu(MultiPageEditorSite.java:562)
at org.eclipse.ui.texteditor.AbstractTextEditor.createPartControl(AbstractTextEditor.java:3540)
at org.eclipse.ui.texteditor.StatusTextEditor.createPartControl(StatusTextEditor.java:54)
at org.eclipse.ui.texteditor.AbstractDecoratedTextEditor.createPartControl(AbstractDecoratedTextEditor.java:447)
at org.eclipse.ui.part.MultiPageEditorPart.addPage(MultiPageEditorPart.java:243)
at org.eclipse.ui.part.MultiPageEditorPart.addPage(MultiPageEditorPart.java:213)
at org.eclipselabs.spray.xtext.ui.editor.SprayMultiPageEditor.createPages(SprayMultiPageEditor.java:56)
at org.eclipse.ui.part.MultiPageEditorPart.createPartControl(MultiPageEditorPart.java:358)
at org.eclipse.ui.internal.e4.compatibility.CompatibilityPart.createPartControl(CompatibilityPart.java:129)
at org.eclipse.ui.internal.e4.compatibility.CompatibilityEditor.createPartControl(CompatibilityEditor.java:95)
at org.eclipse.ui.internal.e4.compatibility.CompatibilityPart.create(CompatibilityPart.java:300)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.e4.core.internal.di.MethodRequestor.execute(MethodRequestor.java:56)
at org.eclipse.e4.core.internal.di.InjectorImpl.processAnnotated(InjectorImpl.java:857)
at org.eclipse.e4.core.internal.di.InjectorImpl.processAnnotated(InjectorImpl.java:837)
at org.eclipse.e4.core.internal.di.InjectorImpl.inject(InjectorImpl.java:111)
at org.eclipse.e4.core.internal.di.InjectorImpl.internalMake(InjectorImpl.java:318)
at org.eclipse.e4.core.internal.di.InjectorImpl.make(InjectorImpl.java:240)
at org.eclipse.e4.core.contexts.ContextInjectionFactory.make(ContextInjectionFactory.java:161)
at org.eclipse.e4.ui.internal.workbench.ReflectionContributionFactory.createFromBundle(ReflectionContributionFactory.java:102)
at org.eclipse.e4.ui.internal.workbench.ReflectionContributionFactory.doCreate(ReflectionContributionFactory.java:71)
at org.eclipse.e4.ui.internal.workbench.ReflectionContributionFactory.create(ReflectionContributionFactory.java:53)
at org.eclipse.e4.ui.workbench.renderers.swt.ContributedPartRenderer.createWidget(ContributedPartRenderer.java:141)
at org.eclipse.e4.ui.internal.workbench.swt.PartRenderingEngine.createWidget(PartRenderingEngine.java:889)
at org.eclipse.e4.ui.internal.workbench.swt.PartRenderingEngine.safeCreateGui(PartRenderingEngine.java:623)
at org.eclipse.e4.ui.internal.workbench.swt.PartRenderingEngine.safeCreateGui(PartRenderingEngine.java:725)
at org.eclipse.e4.ui.internal.workbench.swt.PartRenderingEngine.access$2(PartRenderingEngine.java:696)
at org.eclipse.e4.ui.internal.workbench.swt.PartRenderingEngine$7.run(PartRenderingEngine.java:690)
at org.eclipse.core.runtime.SafeRunner.run(SafeRunner.java:42)
at org.eclipse.e4.ui.internal.workbench.swt.PartRenderingEngine.createGui(PartRenderingEngine.java:675)
at org.eclipse.e4.ui.workbench.renderers.swt.StackRenderer.showTab(StackRenderer.java:1042)
at org.eclipse.e4.ui.workbench.renderers.swt.LazyStackRenderer$1.handleEvent(LazyStackRenderer.java:67)
at org.eclipse.e4.ui.services.internal.events.UIEventHandler$1.run(UIEventHandler.java:41)
at org.eclipse.swt.widgets.Synchronizer.syncExec(Synchronizer.java:180)
at org.eclipse.ui.internal.UISynchronizer.syncExec(UISynchronizer.java:150)
at org.eclipse.swt.widgets.Display.syncExec(Display.java:4687)
at org.eclipse.e4.ui.internal.workbench.swt.E4Application$1.syncExec(E4Application.java:187)
at org.eclipse.e4.ui.services.internal.events.UIEventHandler.handleEvent(UIEventHandler.java:38)
at org.eclipse.equinox.internal.event.EventHandlerWrapper.handleEvent(EventHandlerWrapper.java:197)
at org.eclipse.equinox.internal.event.EventHandlerTracker.dispatchEvent(EventHandlerTracker.java:197)
at org.eclipse.equinox.internal.event.EventHandlerTracker.dispatchEvent(EventHandlerTracker.java:1)
at org.eclipse.osgi.framework.eventmgr.EventManager.dispatchEvent(EventManager.java:230)
at org.eclipse.osgi.framework.eventmgr.ListenerQueue.dispatchEventSynchronous(ListenerQueue.java:148)
at org.eclipse.equinox.internal.event.EventAdminImpl.dispatchEvent(EventAdminImpl.java:135)
at org.eclipse.equinox.internal.event.EventAdminImpl.sendEvent(EventAdminImpl.java:78)
at org.eclipse.equinox.internal.event.EventComponent.sendEvent(EventComponent.java:39)
at org.eclipse.e4.ui.services.internal.events.EventBroker.send(EventBroker.java:81)
at org.eclipse.e4.ui.internal.workbench.UIEventPublisher.notifyChanged(UIEventPublisher.java:57)
at org.eclipse.emf.common.notify.impl.BasicNotifierImpl.eNotify(BasicNotifierImpl.java:374)
at org.eclipse.e4.ui.model.application.ui.impl.ElementContainerImpl.setSelectedElement(ElementContainerImpl.java:171)
at org.eclipse.e4.ui.internal.workbench.ModelServiceImpl.showElementInWindow(ModelServiceImpl.java:418)
at org.eclipse.e4.ui.internal.workbench.ModelServiceImpl.bringToTop(ModelServiceImpl.java:385)
at org.eclipse.e4.ui.internal.workbench.PartServiceImpl.delegateBringToTop(PartServiceImpl.java:578)
at org.eclipse.e4.ui.internal.workbench.PartServiceImpl.bringToTop(PartServiceImpl.java:314)
at org.eclipse.e4.ui.internal.workbench.PartServiceImpl.showPart(PartServiceImpl.java:962)
at org.eclipse.ui.internal.WorkbenchPage.busyOpenEditor(WorkbenchPage.java:3071)
at org.eclipse.ui.internal.WorkbenchPage.access$21(WorkbenchPage.java:2996)
at org.eclipse.ui.internal.WorkbenchPage$8.run(WorkbenchPage.java:2978)
at org.eclipse.swt.custom.BusyIndicator.showWhile(BusyIndicator.java:70)
at org.eclipse.ui.internal.WorkbenchPage.openEditor(WorkbenchPage.java:2974)
at org.eclipse.ui.internal.WorkbenchPage.openEditor(WorkbenchPage.java:2933)
at org.eclipse.ui.internal.WorkbenchPage.openEditor(WorkbenchPage.java:2924)
at org.eclipse.ui.ide.IDE.openEditor(IDE.java:655)
at org.eclipse.ui.ide.IDE.openEditor(IDE.java:614)
at org.eclipse.jdt.internal.ui.javaeditor.EditorUtility.openInEditor(EditorUtility.java:360)
at org.eclipse.jdt.internal.ui.javaeditor.EditorUtility.openInEditor(EditorUtility.java:167)
at org.eclipse.jdt.ui.actions.OpenAction.run(OpenAction.java:249)
at org.eclipse.jdt.ui.actions.OpenAction.run(OpenAction.java:228)
at org.eclipse.jdt.ui.actions.SelectionDispatchAction.dispatchRun(SelectionDispatchAction.java:275)
at org.eclipse.jdt.ui.actions.SelectionDispatchAction.run(SelectionDispatchAction.java:251)
at org.eclipse.jdt.internal.ui.packageview.PackageExplorerActionGroup.handleOpen(PackageExplorerActionGroup.java:376)
at org.eclipse.jdt.internal.ui.packageview.PackageExplorerPart$4.open(PackageExplorerPart.java:538)
at org.eclipse.ui.OpenAndLinkWithEditorHelper$InternalListener.open(OpenAndLinkWithEditorHelper.java:48)
at org.eclipse.jface.viewers.StructuredViewer$2.run(StructuredViewer.java:866)
at org.eclipse.core.runtime.SafeRunner.run(SafeRunner.java:42)
at org.eclipse.ui.internal.JFaceUtil$1.run(JFaceUtil.java:49)
at org.eclipse.jface.util.SafeRunnable.run(SafeRunnable.java:175)
at org.eclipse.jface.viewers.StructuredViewer.fireOpen(StructuredViewer.java:864)
at org.eclipse.jface.viewers.StructuredViewer.handleOpen(StructuredViewer.java:1152)
at org.eclipse.jface.viewers.StructuredViewer$6.handleOpen(StructuredViewer.java:1256)
at org.eclipse.jface.util.OpenStrategy.fireOpenEvent(OpenStrategy.java:275)
at org.eclipse.jface.util.OpenStrategy.access$2(OpenStrategy.java:269)
at org.eclipse.jface.util.OpenStrategy$1.handleEvent(OpenStrategy.java:309)
at org.eclipse.swt.widgets.EventTable.sendEvent(EventTable.java:84)
at org.eclipse.swt.widgets.Widget.sendEvent(Widget.java:1053)
at org.eclipse.swt.widgets.Display.runDeferredEvents(Display.java:4169)
at org.eclipse.swt.widgets.Display.readAndDispatch(Display.java:3758)
at org.eclipse.e4.ui.internal.workbench.swt.PartRenderingEngine$9.run(PartRenderingEngine.java:1022)
at org.eclipse.core.databinding.observable.Realm.runWithDefault(Realm.java:332)
at org.eclipse.e4.ui.internal.workbench.swt.PartRenderingEngine.run(PartRenderingEngine.java:916)
at org.eclipse.e4.ui.internal.workbench.E4Workbench.createAndRunUI(E4Workbench.java:86)
at org.eclipse.ui.internal.Workbench$5.run(Workbench.java:585)
at org.eclipse.core.databinding.observable.Realm.runWithDefault(Realm.java:332)
at org.eclipse.ui.internal.Workbench.createAndRunWorkbench(Workbench.java:540)
at org.eclipse.ui.PlatformUI.createAndRunWorkbench(PlatformUI.java:149)
at org.eclipse.ui.internal.ide.application.IDEApplication.start(IDEApplication.java:124)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:353)
at org.eclipse.core.runtime.adaptor.EclipseStarter.run(EclipseStarter.java:180)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.equinox.launcher.Main.invokeFramework(Main.java:629)
at org.eclipse.equinox.launcher.Main.basicRun(Main.java:584)
at org.eclipse.equinox.launcher.Main.run(Main.java:1438)
at org.eclipse.equinox.launcher.Main.main(Main.java:1414)
28.10.2012 08:58:05 (de.abg.reichert.joerg): Fixed, if there is no properties file found it will be created when opening the multi page editor.
We should keep the mutli page editor so it is assured that the properties file exists and only properties from a properties file having the same name as spray file will be applied in the generation process.
If it is really required to open the spray file with a simple Xtext editor you can still change the plugin.xml in the org.eclipselabs.spray.xtext.ui project and comment out the multipage editor definition and comment in the currently commented out Xtext editor definition.
- stakeholder: Spray user
- keywords: Type: Defect, Priority: Critical
- status: DONE

## issue0192
Reference to EClass cannot be resolved in Juno Modelling + Graphiti + Spray
24.10.2012 10:16:10 (david.rafael.frey): I installe Spray according to
https://spray.ci.cloudbees.com/job/spray-docs-build/lastSuccessfulBuild/artifact/docs/org.eclipselabs.spray.doc.user/docs/html/SprayUserGuide.html#InstallSpray
with 3rd party dependencies on a fresh Eclipse Modelling Edition Juno Service Release 1 (except for one update of the modelling tools) on OS X 10.8.2.
After installing the 3rd party dependencies I was repeatedly facing blocking errors during installation of spray from an archive downloaded here (spray-0.4.0) which all looked like this:
Cannot complete the install because of a conflicting dependency.
Software being installed: Spray SDK Feature 0.4.0.v20120319-1152 (org.eclipselabs.spray.feature.sdk.feature.group 0.4.0.v20120319-1152)
Software currently installed: MWE 2 language SDK 2.3.0.v201206120758 (org.eclipse.emf.mwe2.language.sdk.feature.group 2.3.0.v201206120758)
Only one of the following can be installed at once:
Xtext 2.0.1.v201108020636 (org.eclipse.xtext 2.0.1.v201108020636)
Xtext 1.0.2.v201102150722 (org.eclipse.xtext 1.0.2.v201102150722)
Xtext 2.1.1.v201111141332 (org.eclipse.xtext 2.1.1.v201111141332)
Xtext 2.3.0.v201206120633 (org.eclipse.xtext 2.3.0.v201206120633)
Xtext 2.3.1.v201208210947 (org.eclipse.xtext 2.3.1.v201208210947)
Xtext 2.0.0.v201106070531 (org.eclipse.xtext 2.0.0.v201106070531)
Xtext 2.2.1.v201112130541 (org.eclipse.xtext 2.2.1.v201112130541)
Cannot satisfy dependency:
From: MWE 2 language SDK 2.3.0.v201206120758 (org.eclipse.emf.mwe2.language.sdk.feature.group 2.3.0.v201206120758)
To: org.eclipse.emf.mwe2.launch [2.3.0.v201206120758]
Cannot satisfy dependency:
From: Modeling Workflow Engine 2 Launch 2.3.0.v201206120758 (org.eclipse.emf.mwe2.launch 2.3.0.v201206120758)
To: bundle org.eclipse.xtext [2.3.0,3.0.0)
Cannot satisfy dependency:
From: Spray SDK Feature 0.4.0.v20120319-1152 (org.eclipselabs.spray.feature.sdk.feature.group 0.4.0.v20120319-1152)
To: org.eclipselabs.spray.xtext.tests [0.4.0.v20120319-1152]
Cannot satisfy dependency:
From: Spray Language Runtime 0.4.0.v20120319-1152 (org.eclipselabs.spray.xtext 0.4.0.v20120319-1152)
To: bundle org.eclipse.xtext [2.2.0,2.3.0)
Cannot satisfy dependency:
From: Spray Example &quot;One&quot; - Language Tests 0.4.0.v20120319-1152 (org.eclipselabs.spray.xtext.tests 0.4.0.v20120319-1152)
To: bundle org.eclipselabs.spray.xtext 0.4.0
After uninstalling MWE 2 language SDK, Xtext SDK, Xtext examples and Xbase i was finally able to install spray.
But when i tried to do the tutorial in the Spray user guide (New Spray Project on epackage at http://www.mod4j.org/busmod with diagramm for class BusinessModelDomain) the line
import BusinessDomainDsl.*
diagram busmod for BusinessClass
would result in a @Reference to EClass cannot be resolved. It seems a lot like issue 135, which was supposed to be fixed on juno branch, but I still have the same problem.
?
24.10.2012 10:18:51 (david.rafael.frey): Sorry, the code i provided is not 100% correct, the error occurs on
import BusinessDomainDsl.*
diagram busmod for BusinessDomainModel
28.10.2012 09:11:04 (de.abg.reichert.joerg): version 0.4.0 only works with Eclipse Indigo and does not include the fix for resolving the EClasses.
Instead you should use
3rd party:
https://spray.ci.cloudbees.com/job/spray-ci-targetplatform/lastSuccessfulBuild/artifact/releng/org.eclipselabs.spray.repository/target/repository/
Spray:
https://spray.ci.cloudbees.com/job/spray-assembly-build/lastSuccessfulBuild/artifact/releng/org.eclipselabs.spray.updatesite/target/repository/
Maybe it is even required to download the zip files instead of using the URLs directly.
11.11.2012 01:40:14 (de.abg.reichert.joerg): This issue was closed by revision e494ca97af34.
- stakeholder: Spray user
- keywords: Type: Defect, Priority: Medium
- status: DONE

## issue0193
Unhandled parameter types: [null] in SVG generator
01.11.2012 15:08:12 (joswarmer): Stacktrace happens with BusinesDomain example
!ENTRY org.apache.log4j 4 0 2012-11-01 15:05:19.706
!MESSAGE org.eclipse.xtext.builder.impl.XtextBuilder - Unhandled parameter types: [null]
!STACK 0
java.lang.IllegalArgumentException: Unhandled parameter types: [null]
at org.eclipselabs.spray.shapes.generator.svg.LayoutExtensions.parentX(LayoutExtensions.java:1420)
at org.eclipselabs.spray.shapes.generator.svg.LayoutExtensions._grandParentX(LayoutExtensions.java:902)
at org.eclipselabs.spray.shapes.generator.svg.LayoutExtensions.grandParentX(LayoutExtensions.java:1396)
at org.eclipselabs.spray.shapes.generator.svg.LayoutExtensions._parentX(LayoutExtensions.java:928)
at org.eclipselabs.spray.shapes.generator.svg.LayoutExtensions.parentX(LayoutExtensions.java:1416)
at org.eclipselabs.spray.shapes.generator.svg.LayoutExtensions._grandParentX(LayoutExtensions.java:902)
at org.eclipselabs.spray.shapes.generator.svg.LayoutExtensions.grandParentX(LayoutExtensions.java:1396)
at org.eclipselabs.spray.shapes.generator.svg.LayoutExtensions._parentX(LayoutExtensions.java:928)
at org.eclipselabs.spray.shapes.generator.svg.LayoutExtensions.parentX(LayoutExtensions.java:1416)
at org.eclipselabs.spray.shapes.generator.svg.SVGShapeGenerator._generateShape(SVGShapeGenerator.java:113)
at org.eclipselabs.spray.shapes.generator.svg.SVGShapeGenerator.generateShape(SVGShapeGenerator.java:829)
at org.eclipselabs.spray.shapes.generator.svg.SVGShapeGenerator._generateShape(SVGShapeGenerator.java:355)
at org.eclipselabs.spray.shapes.generator.svg.SVGShapeGenerator.generateShape(SVGShapeGenerator.java:835)
at org.eclipselabs.spray.shapes.generator.svg.SVGShapeGenerator._generate(SVGShapeGenerator.java:63)
at org.eclipselabs.spray.shapes.generator.svg.SVGShapeGenerator.generate(SVGShapeGenerator.java:804)
at org.eclipselabs.spray.shapes.generator.GeneratorSVGDefinition.body(GeneratorSVGDefinition.java:80)
at org.eclipselabs.spray.shapes.generator.GeneratorSVGDefinition.compile(GeneratorSVGDefinition.java:30)
at org.eclipselabs.spray.shapes.generator.ShapeGenerator.doGenerate(ShapeGenerator.java:45)
04.11.2012 17:43:16 (de.abg.reichert.joerg): Fixed on Juno branch (= master)
- stakeholder: Spray user
- keywords: Type: Defect, Priority: Medium
- status: DONE

## issue0194
Moving of elements not working
02.11.2012 20:19:04 (fabio.filippelli): With the new MoveFeature comed in with compartments the elements within the compartments can be moved from one compartment to another, but the main elements on the diagram can not be moved anymore.
1. Create a Node/Class
2. Put it on diagram
3. Try to move the created Node/Class on the diagram.
03.11.2012 10:13:05 (joswarmer):
03.11.2012 19:04:46 (joswarmer): This issue was closed by revision 14203baa36e7.
- stakeholder: Spray user
- keywords: Type: Defect, Priority: Critical, Component: Codegen, OpSys-All, Usability
- status: DONE

## issue0195
AbortCompilation: Pb(324) - class cannot be resolved, indirectly referenced
04.11.2012 15:55:50 (joswarmer): Unclear when this happens, but sometime I get the following stacktrace.
Apart from the stacktrace I see nothing going wrong.
!ENTRY org.eclipse.jdt.core 4 4 2012-11-04 15:47:49.781
!MESSAGE Could not retrieve superclass
!STACK 0
org.eclipse.jdt.internal.compiler.problem.AbortCompilation: Pb(324) The type org.eclipse.xtext.xbase.compiler.JvmModelGenerator cannot be resolved. It is indirectly referenced from required .class files
at org.eclipse.jdt.internal.compiler.problem.ProblemHandler.handle(ProblemHandler.java:135)
at org.eclipse.jdt.internal.compiler.problem.ProblemHandler.handle(ProblemHandler.java:201)
at org.eclipse.jdt.internal.compiler.problem.ProblemReporter.handle(ProblemReporter.java:2132)
at org.eclipse.jdt.internal.compiler.problem.ProblemReporter.isClassPathCorrect(ProblemReporter.java:4162)
at org.eclipse.jdt.internal.compiler.lookup.UnresolvedReferenceBinding.resolve(UnresolvedReferenceBinding.java:59)
at org.eclipse.jdt.internal.compiler.lookup.BinaryTypeBinding.resolveType(BinaryTypeBinding.java:131)
at org.eclipse.jdt.internal.compiler.lookup.BinaryTypeBinding.superclass(BinaryTypeBinding.java:1328)
at org.eclipse.jdt.core.dom.TypeBinding.getSuperclass(TypeBinding.java:807)
at org.eclipse.xtext.common.types.access.jdt.JdtBasedTypeFactory.setSuperTypes(JdtBasedTypeFactory.java:344)
at org.eclipse.xtext.common.types.access.jdt.JdtBasedTypeFactory.createType(JdtBasedTypeFactory.java:124)
at org.eclipse.xtext.common.types.access.jdt.JdtBasedTypeFactory.createType(JdtBasedTypeFactory.java:98)
at org.eclipse.xtext.common.types.access.jdt.JdtBasedTypeFactory.createType(JdtBasedTypeFactory.java:1)
at org.eclipse.xtext.common.types.access.jdt.JdtTypeMirror.initialize(JdtTypeMirror.java:36)
at org.eclipse.xtext.common.types.access.TypeResource.doLoad(TypeResource.java:93)
at org.eclipse.emf.ecore.resource.impl.ResourceImpl.load(ResourceImpl.java:1505)
at org.eclipse.xtext.common.types.access.TypeResource.load(TypeResource.java:80)
at org.eclipse.emf.ecore.resource.impl.ResourceSetImpl.demandLoad(ResourceSetImpl.java:259)
at org.eclipse.emf.ecore.resource.impl.ResourceSetImpl.demandLoadHelper(ResourceSetImpl.java:274)
at org.eclipse.xtext.resource.XtextResourceSet.getResource(XtextResourceSet.java:159)
at org.eclipse.xtext.common.types.access.jdt.JdtTypeProvider.getResourceForJavaURI(JdtTypeProvider.java:120)
at org.eclipse.xtext.common.types.access.jdt.JdtTypeProvider.findTypeByName(JdtTypeProvider.java:102)
at org.eclipse.xtext.common.types.xtext.AbstractTypeScope.getSingleElement(AbstractTypeScope.java:54)
at org.eclipse.xtext.scoping.impl.AbstractScope.getSingleElement(AbstractScope.java:105)
at org.eclipse.xtext.linking.impl.DefaultLinkingService.getLinkedObjects(DefaultLinkingService.java:121)
at org.eclipse.xtext.linking.lazy.LazyLinkingResource.getEObject(LazyLinkingResource.java:179)
at org.eclipse.xtext.xbase.resource.XbaseResource.access$0(XbaseResource.java:1)
at org.eclipse.xtext.xbase.resource.XbaseResource$2.exec(XbaseResource.java:239)
at org.eclipse.xtext.xbase.resource.XbaseResource$2.exec(XbaseResource.java:1)
at org.eclipse.xtext.util.OnChangeEvictingCache.execWithoutCacheClear(OnChangeEvictingCache.java:124)
at org.eclipse.xtext.xbase.resource.XbaseResource.getEObject(XbaseResource.java:237)
at org.eclipse.xtend.core.resource.XtendResource.getEObject(XtendResource.java:82)
at org.eclipse.xtext.linking.lazy.LazyLinkingResource.resolveLazyCrossReference(LazyLinkingResource.java:147)
at org.eclipse.xtext.linking.lazy.LazyLinkingResource.resolveLazyCrossReferences(LazyLinkingResource.java:108)
at org.eclipse.xtext.EcoreUtil2.resolveLazyCrossReferences(EcoreUtil2.java:497)
at org.eclipse.xtext.builder.clustering.ClusteringBuilderState.doUpdate(ClusteringBuilderState.java:204)
at org.eclipse.xtext.builder.builderState.AbstractBuilderState.update(AbstractBuilderState.java:105)
at org.eclipse.xtext.builder.impl.XtextBuilder.doBuild(XtextBuilder.java:159)
at org.eclipse.xtext.builder.impl.XtextBuilder.fullBuild(XtextBuilder.java:188)
at org.eclipse.xtext.builder.impl.XtextBuilder.build(XtextBuilder.java:85)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:321)
at org.eclipse.core.internal.events.BuildManager.build(BuildManager.java:396)
at org.eclipse.core.internal.resources.Project$1.run(Project.java:618)
at org.eclipse.core.internal.resources.Workspace.run(Workspace.java:2344)
at org.eclipse.core.internal.resources.Project.internalBuild(Project.java:597)
at org.eclipse.core.internal.resources.Project.build(Project.java:124)
at org.eclipse.xtext.builder.impl.BuildScheduler$BuildJob.run(BuildScheduler.java:178)
at org.eclipse.core.internal.jobs.Worker.run(Worker.java:54)
04.11.2012 17:42:29 (de.abg.reichert.joerg): I've had seen this from time to time, too. Maybe a problem with type inference, where the return type of method should be defined explicitly or there is a dependent library missing on the classpath, I will have a look at it.
https://bugs.eclipse.org/bugs/show_bug.cgi?id=352706
12.11.2012 17:49:52 (joswarmer): The problem seems to start from the JDT, which needs to find the xbase compiler. It seems we need to put the xbase compiler in the MANIFEST of the JDT. That is very much outside our scope.
12.11.2012 17:50:21 (joswarmer):
05.12.2012 19:35:09 (de.abg.reichert.joerg): !ENTRY org.eclipse.jdt.core 4 4 2012-11-29 18:40:02.921
!MESSAGE Could not retrieve superclass
!STACK 0
org.eclipse.jdt.internal.compiler.problem.AbortCompilation: Pb(324) The type org.eclipse.xtext.xbase.compiler.XbaseCompiler cannot be resolved. It is indirectly referenced from required .class files
at org.eclipse.jdt.internal.compiler.problem.ProblemHandler.handle(ProblemHandler.java:135)
at org.eclipse.jdt.internal.compiler.problem.ProblemHandler.handle(ProblemHandler.java:201)
at org.eclipse.jdt.internal.compiler.problem.ProblemReporter.handle(ProblemReporter.java:2132)
at org.eclipse.jdt.internal.compiler.problem.ProblemReporter.isClassPathCorrect(ProblemReporter.java:4162)
at org.eclipse.jdt.internal.compiler.lookup.UnresolvedReferenceBinding.resolve(UnresolvedReferenceBinding.java:59)
at org.eclipse.jdt.internal.compiler.lookup.BinaryTypeBinding.resolveType(BinaryTypeBinding.java:131)
at org.eclipse.jdt.internal.compiler.lookup.BinaryTypeBinding.superclass(BinaryTypeBinding.java:1328)
at org.eclipse.jdt.core.dom.TypeBinding.getSuperclass(TypeBinding.java:807)
at org.eclipse.xtext.common.types.access.jdt.JdtBasedTypeFactory.setSuperTypes(JdtBasedTypeFactory.java:344)
at org.eclipse.xtext.common.types.access.jdt.JdtBasedTypeFactory.createType(JdtBasedTypeFactory.java:124)
at org.eclipse.xtext.common.types.access.jdt.JdtBasedTypeFactory.createType(JdtBasedTypeFactory.java:98)
at org.eclipse.xtext.common.types.access.jdt.JdtBasedTypeFactory.createType(JdtBasedTypeFactory.java:1)
at org.eclipse.xtext.common.types.access.jdt.JdtTypeMirror.initialize(JdtTypeMirror.java:36)
at org.eclipse.xtext.common.types.access.TypeResource.doLoad(TypeResource.java:93)
at org.eclipse.emf.ecore.resource.impl.ResourceImpl.load(ResourceImpl.java:1505)
at org.eclipse.xtext.common.types.access.TypeResource.load(TypeResource.java:80)
at org.eclipse.emf.ecore.resource.impl.ResourceSetImpl.demandLoad(ResourceSetImpl.java:259)
at org.eclipse.emf.ecore.resource.impl.ResourceSetImpl.demandLoadHelper(ResourceSetImpl.java:274)
at org.eclipse.xtext.resource.XtextResourceSet.getResource(XtextResourceSet.java:159)
at org.eclipse.xtext.common.types.access.jdt.JdtTypeProvider.getResourceForJavaURI(JdtTypeProvider.java:120)
at org.eclipse.xtext.common.types.access.jdt.JdtTypeProvider.findTypeByName(JdtTypeProvider.java:102)
at org.eclipse.xtext.common.types.xtext.AbstractTypeScope.getSingleElement(AbstractTypeScope.java:54)
at org.eclipse.xtext.scoping.impl.AbstractScope.getSingleElement(AbstractScope.java:105)
at org.eclipse.xtext.linking.impl.DefaultLinkingService.getLinkedObjects(DefaultLinkingService.java:121)
at org.eclipse.xtext.linking.lazy.LazyLinkingResource.getEObject(LazyLinkingResource.java:179)
at org.eclipse.xtext.xbase.resource.XbaseResource.access$0(XbaseResource.java:1)
at org.eclipse.xtext.xbase.resource.XbaseResource$2.exec(XbaseResource.java:239)
at org.eclipse.xtext.xbase.resource.XbaseResource$2.exec(XbaseResource.java:1)
at org.eclipse.xtext.util.OnChangeEvictingCache.execWithoutCacheClear(OnChangeEvictingCache.java:124)
at org.eclipse.xtext.xbase.resource.XbaseResource.getEObject(XbaseResource.java:237)
at org.eclipse.xtend.core.resource.XtendResource.getEObject(XtendResource.java:82)
at org.eclipse.xtext.linking.lazy.LazyLinkingResource.resolveLazyCrossReference(LazyLinkingResource.java:147)
at org.eclipse.xtext.linking.lazy.LazyLinkingResource.resolveLazyCrossReferences(LazyLinkingResource.java:108)
at org.eclipse.xtext.EcoreUtil2.resolveLazyCrossReferences(EcoreUtil2.java:497)
at org.eclipse.xtext.builder.clustering.ClusteringBuilderState.doUpdate(ClusteringBuilderState.java:204)
at org.eclipse.xtext.builder.builderState.AbstractBuilderState.update(AbstractBuilderState.java:105)
at org.eclipse.xtext.builder.impl.XtextBuilder.doBuild(XtextBuilder.java:159)
at org.eclipse.xtext.builder.impl.XtextBuilder.fullBuild(XtextBuilder.java:188)
at org.eclipse.xtext.builder.impl.XtextBuilder.build(XtextBuilder.java:85)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:321)
at org.eclipse.core.internal.events.BuildManager.build(BuildManager.java:396)
at org.eclipse.core.internal.resources.Project$1.run(Project.java:618)
at org.eclipse.core.internal.resources.Workspace.run(Workspace.java:2344)
at org.eclipse.core.internal.resources.Project.internalBuild(Project.java:597)
at org.eclipse.core.internal.resources.Project.build(Project.java:124)
at org.eclipse.xtext.builder.impl.BuildScheduler$BuildJob.run(BuildScheduler.java:178)
at org.eclipse.core.internal.jobs.Worker.run(Worker.java:53)
05.12.2012 19:36:12 (de.abg.reichert.joerg): !ENTRY org.eclipse.jdt.core 4 4 2012-11-29 18:40:08.308
!MESSAGE Could not retrieve superclass
!STACK 0
org.eclipse.jdt.internal.compiler.problem.AbortCompilation: Pb(324) The type org.eclipselabs.spray.xtext.SprayStandaloneSetup cannot be resolved. It is indirectly referenced from required .class files
at org.eclipse.jdt.internal.compiler.problem.ProblemHandler.handle(ProblemHandler.java:135)
at org.eclipse.jdt.internal.compiler.problem.ProblemHandler.handle(ProblemHandler.java:201)
at org.eclipse.jdt.internal.compiler.problem.ProblemReporter.handle(ProblemReporter.java:2132)
at org.eclipse.jdt.internal.compiler.problem.ProblemReporter.isClassPathCorrect(ProblemReporter.java:4162)
at org.eclipse.jdt.internal.compiler.lookup.UnresolvedReferenceBinding.resolve(UnresolvedReferenceBinding.java:59)
at org.eclipse.jdt.internal.compiler.lookup.BinaryTypeBinding.resolveType(BinaryTypeBinding.java:131)
at org.eclipse.jdt.internal.compiler.lookup.BinaryTypeBinding.superclass(BinaryTypeBinding.java:1328)
at org.eclipse.jdt.core.dom.TypeBinding.getSuperclass(TypeBinding.java:807)
at org.eclipse.xtext.common.types.access.jdt.JdtBasedTypeFactory.setSuperTypes(JdtBasedTypeFactory.java:344)
at org.eclipse.xtext.common.types.access.jdt.JdtBasedTypeFactory.createType(JdtBasedTypeFactory.java:124)
at org.eclipse.xtext.common.types.access.jdt.JdtBasedTypeFactory.createType(JdtBasedTypeFactory.java:98)
at org.eclipse.xtext.common.types.access.jdt.JdtBasedTypeFactory.createType(JdtBasedTypeFactory.java:1)
at org.eclipse.xtext.common.types.access.jdt.JdtTypeMirror.initialize(JdtTypeMirror.java:36)
at org.eclipse.xtext.common.types.access.TypeResource.doLoad(TypeResource.java:93)
at org.eclipse.emf.ecore.resource.impl.ResourceImpl.load(ResourceImpl.java:1505)
at org.eclipse.xtext.common.types.access.TypeResource.load(TypeResource.java:80)
at org.eclipse.emf.ecore.resource.impl.ResourceSetImpl.demandLoad(ResourceSetImpl.java:259)
at org.eclipse.emf.ecore.resource.impl.ResourceSetImpl.demandLoadHelper(ResourceSetImpl.java:274)
at org.eclipse.xtext.resource.XtextResourceSet.getResource(XtextResourceSet.java:159)
at org.eclipse.xtext.common.types.access.jdt.JdtTypeProvider.getResourceForJavaURI(JdtTypeProvider.java:120)
at org.eclipse.xtext.common.types.access.jdt.JdtTypeProvider.findTypeByName(JdtTypeProvider.java:102)
at org.eclipse.xtext.common.types.xtext.AbstractTypeScope.getSingleElement(AbstractTypeScope.java:54)
at org.eclipse.xtext.linking.impl.ImportedNamesAdapter$WrappingScope.getSingleElement(ImportedNamesAdapter.java:56)
at org.eclipse.xtext.scoping.impl.AbstractScope.getSingleElement(AbstractScope.java:105)
at org.eclipse.xtext.scoping.impl.AbstractScope.getSingleElement(AbstractScope.java:105)
at org.eclipse.xtext.scoping.impl.AbstractScope.getSingleElement(AbstractScope.java:105)
at org.eclipse.xtext.scoping.impl.AbstractScope.getSingleElement(AbstractScope.java:105)
at org.eclipse.xtext.linking.impl.DefaultLinkingService.getLinkedObjects(DefaultLinkingService.java:121)
at org.eclipse.xtext.linking.lazy.LazyLinkingResource.getEObject(LazyLinkingResource.java:179)
at org.eclipse.xtext.linking.lazy.LazyLinkingResource.resolveLazyCrossReference(LazyLinkingResource.java:147)
at org.eclipse.xtext.linking.lazy.LazyLinkingResource.resolveLazyCrossReferences(LazyLinkingResource.java:108)
at org.eclipse.xtext.EcoreUtil2.resolveLazyCrossReferences(EcoreUtil2.java:497)
at org.eclipse.xtext.builder.clustering.ClusteringBuilderState.doUpdate(ClusteringBuilderState.java:204)
at org.eclipse.xtext.builder.builderState.AbstractBuilderState.update(AbstractBuilderState.java:105)
at org.eclipse.xtext.builder.impl.XtextBuilder.doBuild(XtextBuilder.java:159)
at org.eclipse.xtext.builder.impl.XtextBuilder.fullBuild(XtextBuilder.java:188)
at org.eclipse.xtext.builder.impl.XtextBuilder.build(XtextBuilder.java:85)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:321)
at org.eclipse.core.internal.events.BuildManager.build(BuildManager.java:396)
at org.eclipse.core.internal.resources.Project$1.run(Project.java:618)
at org.eclipse.core.internal.resources.Workspace.run(Workspace.java:2344)
at org.eclipse.core.internal.resources.Project.internalBuild(Project.java:597)
at org.eclipse.core.internal.resources.Project.build(Project.java:124)
at org.eclipse.xtext.builder.impl.BuildScheduler$BuildJob.run(BuildScheduler.java:178)
at org.eclipse.core.internal.jobs.Worker.run(Worker.java:53)
05.12.2012 19:48:36 (de.abg.reichert.joerg): !ENTRY org.eclipse.jdt.core 4 4 2012-12-04 21:18:32.300
!MESSAGE Could not retrieve superclass
!STACK 0
org.eclipse.jdt.internal.compiler.problem.AbortCompilation: Pb(324) The type org.eclipse.xtext.generator.Generator cannot be resolved. It is indirectly referenced from required .class files
at org.eclipse.jdt.internal.compiler.problem.ProblemHandler.handle(ProblemHandler.java:135)
at org.eclipse.jdt.internal.compiler.problem.ProblemHandler.handle(ProblemHandler.java:201)
at org.eclipse.jdt.internal.compiler.problem.ProblemReporter.handle(ProblemReporter.java:2132)
at org.eclipse.jdt.internal.compiler.problem.ProblemReporter.isClassPathCorrect(ProblemReporter.java:4162)
at org.eclipse.jdt.internal.compiler.lookup.UnresolvedReferenceBinding.resolve(UnresolvedReferenceBinding.java:59)
at org.eclipse.jdt.internal.compiler.lookup.BinaryTypeBinding.resolveType(BinaryTypeBinding.java:131)
at org.eclipse.jdt.internal.compiler.lookup.BinaryTypeBinding.superclass(BinaryTypeBinding.java:1328)
at org.eclipse.jdt.core.dom.TypeBinding.getSuperclass(TypeBinding.java:807)
at org.eclipse.xtext.common.types.access.jdt.JdtBasedTypeFactory.setSuperTypes(JdtBasedTypeFactory.java:345)
at org.eclipse.xtext.common.types.access.jdt.JdtBasedTypeFactory.createType(JdtBasedTypeFactory.java:124)
at org.eclipse.xtext.common.types.access.jdt.JdtBasedTypeFactory.createType(JdtBasedTypeFactory.java:98)
at org.eclipse.xtext.common.types.access.jdt.JdtBasedTypeFactory.createType(JdtBasedTypeFactory.java:1)
at org.eclipse.xtext.common.types.access.jdt.JdtTypeMirror.initialize(JdtTypeMirror.java:36)
at org.eclipse.xtext.common.types.access.TypeResource.doLoad(TypeResource.java:93)
at org.eclipse.emf.ecore.resource.impl.ResourceImpl.load(ResourceImpl.java:1505)
at org.eclipse.xtext.common.types.access.TypeResource.load(TypeResource.java:80)
at org.eclipse.emf.ecore.resource.impl.ResourceSetImpl.demandLoad(ResourceSetImpl.java:259)
at org.eclipse.emf.ecore.resource.impl.ResourceSetImpl.demandLoadHelper(ResourceSetImpl.java:274)
at org.eclipse.xtext.resource.XtextResourceSet.getResource(XtextResourceSet.java:159)
at org.eclipse.xtext.common.types.access.jdt.JdtTypeProvider.getResourceForJavaURI(JdtTypeProvider.java:120)
at org.eclipse.xtext.common.types.access.jdt.JdtTypeProvider.findTypeByName(JdtTypeProvider.java:102)
at org.eclipse.xtext.common.types.xtext.AbstractTypeScope.getSingleElement(AbstractTypeScope.java:54)
at org.eclipse.xtext.linking.impl.ImportedNamesAdapter$WrappingScope.getSingleElement(ImportedNamesAdapter.java:56)
at org.eclipse.xtext.scoping.impl.AbstractScope.getSingleElement(AbstractScope.java:105)
at org.eclipse.xtext.scoping.impl.AbstractScope.getSingleElement(AbstractScope.java:105)
at org.eclipse.xtext.scoping.impl.AbstractScope.getSingleElement(AbstractScope.java:105)
at org.eclipse.xtext.scoping.impl.AbstractScope.getSingleElement(AbstractScope.java:105)
at org.eclipse.xtext.linking.impl.DefaultLinkingService.getLinkedObjects(DefaultLinkingService.java:121)
at org.eclipse.xtext.linking.lazy.LazyLinkingResource.getEObject(LazyLinkingResource.java:179)
at org.eclipse.xtext.linking.lazy.LazyLinkingResource.resolveLazyCrossReference(LazyLinkingResource.java:147)
at org.eclipse.xtext.linking.lazy.LazyLinkingResource.resolveLazyCrossReferences(LazyLinkingResource.java:108)
at org.eclipse.xtext.EcoreUtil2.resolveLazyCrossReferences(EcoreUtil2.java:497)
at org.eclipse.xtext.builder.clustering.ClusteringBuilderState.doUpdate(ClusteringBuilderState.java:204)
at org.eclipse.xtext.builder.builderState.AbstractBuilderState.update(AbstractBuilderState.java:105)
at org.eclipse.xtext.builder.impl.XtextBuilder.doBuild(XtextBuilder.java:159)
at org.eclipse.xtext.builder.impl.XtextBuilder.fullBuild(XtextBuilder.java:188)
at org.eclipse.xtext.builder.impl.XtextBuilder.build(XtextBuilder.java:85)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:321)
at org.eclipse.core.internal.events.BuildManager.build(BuildManager.java:396)
at org.eclipse.core.internal.resources.Project$1.run(Project.java:618)
at org.eclipse.core.internal.resources.Workspace.run(Workspace.java:2344)
at org.eclipse.core.internal.resources.Project.internalBuild(Project.java:597)
at org.eclipse.core.internal.resources.Project.build(Project.java:124)
at org.eclipse.xtext.builder.impl.BuildScheduler$BuildJob.run(BuildScheduler.java:178)
at org.eclipse.core.internal.jobs.Worker.run(Worker.java:53)
- stakeholder: Spray user
- keywords: Type: Defect, Priority: Medium
- status: READY

## issue0196
NPE in adjustPriority(...)
10.11.2012 18:46:06 (joswarmer): Sometimes I get a NPE:
Caused by: java.lang.NullPointerException
at org.eclipselabs.spray.xtext.ui.contentassist.SprayJdtTypesProposalPriorities.adjustPriority(SprayJdtTypesProposalPriorities.java:10)
at org.eclipse.xtext.ui.editor.contentassist.ContentProposalPriorities.adjustKeywordPriority(ContentProposalPriorities.java:38)
at org.eclipse.xtext.ui.editor.contentassist.AbstractJavaBasedContentProposalProvider.completeKeyword(AbstractJavaBasedContentProposalProvider.java:167)
at org.eclipse.xtext.xbase.ui.contentassist.XbaseProposalProvider.completeKeyword(XbaseProposalProvider.java:222)
at org.eclipselabs.spray.xtext.ui.contentassist.SprayProposalProvider.completeKeyword(SprayProposalProvider.java:222)
at org.eclipse.xtext.ui.editor.contentassist.AbstractContentProposalProvider$DefaultContentAssistProcessorSwitch.caseKeyword(AbstractContentProposalProvider.java:54)
at org.eclipse.xtext.ui.editor.contentassist.AbstractContentProposalProvider$DefaultContentAssistProcessorSwitch.caseKeyword(AbstractContentProposalProvider.java:1)
at org.eclipse.xtext.util.XtextSwitch.doSwitch(XtextSwitch.java:150)
at org.eclipse.xtext.util.XtextSwitch.doSwitch(XtextSwitch.java:70)
at org.eclipse.xtext.util.XtextSwitch.doSwitch(XtextSwitch.java:58)
at org.eclipse.xtext.ui.editor.contentassist.AbstractContentProposalProvider$DefaultContentAssistProcessorSwitch.accept(AbstractContentProposalProvider.java:71)
at org.eclipse.xtext.ui.editor.contentassist.AbstractContentProposalProvider.createProposals(AbstractContentProposalProvider.java:108)
at org.eclipse.xtext.ui.editor.contentassist.AbstractJavaBasedContentProposalProvider.createProposals(AbstractJavaBasedContentProposalProvider.java:246)
at org.eclipse.xtext.ui.editor.contentassist.CompletionProposalComputer.exec(CompletionProposalComputer.java:51)
at org.eclipse.xtext.ui.editor.contentassist.CompletionProposalComputer.exec(CompletionProposalComputer.java:1)
at org.eclipse.xtext.util.concurrent.AbstractReadWriteAcces.readOnly(AbstractReadWriteAcces.java:32)
at org.eclipse.xtext.ui.editor.model.XtextDocument.readOnly(XtextDocument.java:78)
at org.eclipse.xtext.ui.editor.contentassist.XtextContentAssistProcessor.computeCompletionProposals(XtextContentAssistProcessor.java:68)
at org.eclipse.xtext.ui.editor.contentassist.RepeatedContentAssistProcessor.computeCompletionProposals(RepeatedContentAssistProcessor.java:73)
at org.eclipse.jface.text.contentassist.ContentAssistant.computeCompletionProposals(ContentAssistant.java:1839)
at org.eclipse.jface.text.contentassist.CompletionProposalPopup.computeProposals(CompletionProposalPopup.java:566)
at org.eclipse.jface.text.contentassist.CompletionProposalPopup.computeFilteredProposals(CompletionProposalPopup.java:1460)
at org.eclipse.jface.text.contentassist.CompletionProposalPopup.access$4(CompletionProposalPopup.java:1449)
at org.eclipse.jface.text.contentassist.CompletionProposalPopup$1.run(CompletionProposalPopup.java:375)
at org.eclipse.swt.widgets.RunnableLock.run(RunnableLock.java:35)
at org.eclipse.swt.widgets.Synchronizer.runAsyncMessages(Synchronizer.java:135)
10.11.2012 19:25:39 (joswarmer): Added test for null proposal, as was also in the overwritten method.
- stakeholder: Spray user
- keywords: Type: Defect, Priority: Medium
- status: DONE

## issue0197
Change documentation to use compartments
10.11.2012 19:20:01 (joswarmer): The new compartments should replace the container concept in the Spray DSL. All documentation and 5/15 minute tutorials should be changed to use compartments.
12.11.2012 17:02:42 (joswarmer):
19.11.2012 16:50:23 (joswarmer):
- stakeholder: Spray user
- keywords: Type: Task, Priority: Medium
- status: DONE

## issue0198
Allow the user to change the order of the shapes in a compartment
11.11.2012 17:38:14 (joswarmer): From Fabio: In a compartment the order of the shapes currently always is the order in which they were added. It would be useful to allow users to change this order. E.g. you start with
Class: MyClass
- PropertyOne
- PropertyTwo
Now the user wants to switch this properties in a different way (PropertyTwo before PropertyOne)
MyClass
- PropertyTwo
- PropertyOne
19.11.2012 16:51:54 (joswarmer):
- stakeholder: Spray user
- keywords: Type: Enhancement
- status: READY

## issue0199
Class cast exception in style DSL
11.11.2012 19:18:34 (joswarmer): Code completion proposal after 'extend' without the 'JAVA' keyword results in the following exception.
ENTRY org.apache.log4j 2 0 2012-11-11 19:15:41.575
!MESSAGE org.eclipse.xtext.ui.editor.contentassist.AbstractJavaBasedContentProposalProvider - Error in polymorphic dispatcher : org.eclipselabs.spray.styles.scoping.StyleScopeProvider cannot be cast to org.eclipse.xtext.xbase.scoping.XbaseScopeProvider
!STACK 0
java.lang.ClassCastException: org.eclipselabs.spray.styles.scoping.StyleScopeProvider cannot be cast to org.eclipse.xtext.xbase.scoping.XbaseScopeProvider
at org.eclipse.xtext.xbase.ui.contentassist.XbaseProposalProvider.getScopeProvider(XbaseProposalProvider.java:232)
at org.eclipse.xtext.xbase.ui.contentassist.XbaseProposalProvider.lookupCrossReference(XbaseProposalProvider.java:355)
at org.eclipse.xtext.ui.editor.contentassist.AbstractJavaBasedContentProposalProvider.lookupCrossReference(AbstractJavaBasedContentProposalProvider.java:205)
at org.eclipse.xtext.xbase.ui.contentassist.XbaseProposalProvider.lookupCrossReference(XbaseProposalProvider.java:238)
at org.eclipselabs.spray.styles.ui.contentassist.AbstractStyleProposalProvider.completeStyle_SuperStyleFromDsl(AbstractStyleProposalProvider.java:30)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.xtext.util.PolymorphicDispatcher.invoke(PolymorphicDispatcher.java:291)
at org.eclipse.xtext.ui.editor.contentassist.AbstractJavaBasedContentProposalProvider.invokeMethod(AbstractJavaBasedContentProposalProvider.java:271)
at org.eclipse.xtext.ui.editor.contentassist.AbstractJavaBasedContentProposalProvider.completeAssignment(AbstractJavaBasedContentProposalProvider.java:185)
at org.eclipse.xtext.ui.editor.contentassist.AbstractContentProposalProvider$DefaultContentAssistProcessorSwitch.caseAssignment(AbstractContentProposalProvider.java:66)
at org.eclipse.xtext.ui.editor.contentassist.AbstractContentProposalProvider$DefaultContentAssistProcessorSwitch.caseAssignment(AbstractContentProposalProvider.java:1)
at org.eclipse.xtext.util.XtextSwitch.doSwitch(XtextSwitch.java:164)
11.11.2012 22:53:48 (de.abg.reichert.joerg): This issue was closed by revision 205621ad378f.
- stakeholder: Spray user
- keywords: Type: Defect, Priority: Medium
- status: DONE

## issue0200
Fix outline views
18.11.2012 16:30:10 (de.abg.reichert.joerg): Currently the outline views of Spray, Shape and Style DSL are not adapted to the recent DSL changes, so a lot of unnamed/misnamed nodes appear there.
When editing a large Shape model this currently causes a lot of flickering of the outline view - this should be fixed either by restricting the depth of shown children or by adding some laziness to the recalculation of the outline view tree.
19.11.2012 16:49:53 (joswarmer):
- stakeholder: Spray user
- keywords: Type: Task
- status: DONE

## issue0201
Constant generated with white spaces
18.11.2012 17:03:24 (de.abg.reichert.joerg): class MyElement {
shape org.eclipselabs.spray.shapes.MyShape
behavior {
create into myElements palette &quot;My elements&quot;
}
}
generates to GraphitiToolBehaviorProviderBase
public abstract class GraphitiToolBehaviorProviderBase extends AbstractSprayToolBehaviorProvider {
...
protected static final String MY ELEMENTS = &quot;My elements&quot;;
...
}
-&gt; the constant contains an invalid white space.
The generator should filter out all characters that would be invalid in Java variable name.
19.11.2012 12:50:56 (joswarmer):
19.11.2012 12:51:19 (joswarmer): This issue was closed by revision 85ff95298147.
- stakeholder: Spray user
- keywords: Type: Defect, Priority: Low
- status: DONE

## issue0202
Write automated tests for the generated diagram editors
18.11.2012 18:03:59 (de.abg.reichert.joerg): There are currently some bugs in the generated diagram editors that should be disovered inside the automated build.
I have checked in some example diagram projects done with our example DSL projects:
* http://code.google.com/a/eclipselabs.org/p/spray/source/browse/examples/bpmn2.0/org.eclipselabs.spray.examples.bpmn.diagrams
* http://code.google.com/a/eclipselabs.org/p/spray/source/browse/examples/fowlerdsl/org.eclipse.xtext.example.fowlerdsl.diagrams
* http://code.google.com/a/eclipselabs.org/p/spray/source/browse/examples/fowlerdsl/org.eclipse.xtext.example.fowlerdsl.diagrams
* http://code.google.com/a/eclipselabs.org/p/spray/source/browse/examples/lwc2012/org.eclipselabs.spray.examples.lwc2012.diagrams
* http://code.google.com/a/eclipselabs.org/p/spray/source/browse/examples/one/org.eclipselabs.spray.examples.one.diagrams
* http://code.google.com/a/eclipselabs.org/p/spray/source/browse/examples/petrinet/org.eclipselabs.spray.examples.petrinet.diagrams
For how to test, see the following resources:
Graphiti Dark Feature Processing
* http://help.eclipse.org/juno/index.jsp?topic=%2Forg.eclipse.graphiti.doc%2Fresources%2Fdocu%2Fgfw%2Fdark-feature-processing.htm
* http://5ise.quanxinquanyi.de/2012/08/06/testing-graphiti-applications-with-dark-feature-processing/
Graphiti SWTBot Tests
* http://git.eclipse.org/c/gmp/org.eclipse.gmp.graphiti.git/tree/tests/org.eclipse.graphiti.bot.tests
* I (Joerg) actually developed some Graphiti SWTBot tests to, I should make the generic factored out super/helper classes available to Spray
See also the already existing SWTBot test for the Spray wizard (that currently fails)
* http://code.google.com/a/eclipselabs.org/p/spray/issues/detail?id=8
* http://code.google.com/a/eclipselabs.org/p/spray/source/browse/tests/org.eclipselabs.spray.examples.one.tests/pom.xml
The tests should be part of the example project builds: After having build the diagram DSL project an Eclipse instance should be started with the just build diagram DSL plug-in and creating a new diagram, adding and updating shapes should be tested either as SWTBot tests or dark feature processing tests.
For test concepts see here:
https://spray.ci.cloudbees.com/job/spray-docs-build/lastSuccessfulBuild/artifact/docs/org.eclipselabs.spray.doc.dev/docs/html/SprayDeveloperGuide.html#TestingthegeneratedGraphitieditor
- stakeholder: Spray user
- keywords: Type: Task
- status: OPEN

## issue0203
FDrag and drop of shapes only takes the top shape
19.11.2012 15:06:23 (joswarmer): When doping a drag and drop for a shape into another container, only the top shape of the dragged shape is moved. The children are all ignored. Of course the complete shape including its children should be moved.
19.11.2012 16:51:10 (joswarmer):
10.12.2012 13:23:55 (joswarmer): Avoid using the add feature, instead manipulate the shapes directly.
10.12.2012 13:27:11 (joswarmer): This issue was closed by revision 3a06b18dab8e.
10.12.2012 14:01:34 (joswarmer): Tested with business domain DSL. All nested shapes and objects are moved as well now.
- stakeholder: Spray user
- keywords: Type: Defect, Priority: Medium
- status: DONE

## issue0204
Default implementation for associating EObjects to associations
19.11.2012 16:52:51 (de.abg.reichert.joerg): I just tested this a week ago, there seem to be no EObjects linked with connections so they appear as red dotted lines:
http://spray.eclipselabs.org.codespot.com/git/examples/bpmn2.0/org.eclipselabs.spray.examples.bpmn.diagrams/receipt/receipt.PNG
19.11.2012 17:05:40 (joswarmer):
17.05.2013 17:01:37 (de.abg.reichert.joerg): should be fixed by the fix of issue #241. Problem wasn't the missing associated EObject but a bug in the update feature for connections.
- stakeholder: Spray user
- keywords: Type: Defect, Priority: Medium
- status: DONE

## issue0205
Resize of shapes containing texts ugly
19.11.2012 17:00:35 (de.abg.reichert.joerg): Also experienced one week ago, when resizing a shape containing a text, e.g. dragging the right edge of the shape more and more to the right, the text wanders torwards the right edge until it disappears.
http://spray.eclipselabs.org.codespot.com/git/examples/bpmn2.0/org.eclipselabs.spray.examples.bpmn.diagrams/receipt/receipt.PNG
19.11.2012 17:01:25 (de.abg.reichert.joerg):
19.11.2012 17:06:31 (joswarmer):
19.11.2012 17:21:31 (joswarmer): Can you explain in what circumstances, or attach the style/shape and spray files ? I cannot reproduce this behavior in the examples I use.
19.11.2012 17:39:04 (de.abg.reichert.joerg): I used the BPMN2 example project:
http://code.google.com/a/eclipselabs.org/p/spray/source/browse/#git%2Fexamples%2Fbpmn2.0%2Forg.eclipselabs.spray.examples.bpmn
and created an example diagram:
http://code.google.com/a/eclipselabs.org/p/spray/source/browse/#git%2Fexamples%2Fbpmn2.0%2Forg.eclipselabs.spray.examples.bpmn.diagrams%2Freceipt
I had this behavior on 11/11/12, I did not test if this has been fixed in the mean time.
19.11.2012 19:13:18 (joswarmer): I see, the horizontal-align=center of the text is taken in relationship with the text object, not in relation with the parent rectangle. And the text size grows shrinks with the text, which it should not.
- stakeholder: Spray user
- keywords: Type: Defect, Priority: Medium
- status: READY

## issue0206
Referenced gradient leads to shape generator abort
20.11.2012 19:31:28 (de.abg.reichert.joerg): style
style MyDefaultStyle {
description = &quot;The default style of the graphiti diagram type.&quot;
transparency = 1.00
// background-color = black
line-color = black
line-style = solid
line-width = 1
font-color = black
font-name = &quot;Tahoma&quot;
font-size = 12
font-bold = yes
}
style EntryStyle extends MyDefaultStyle {
background-color = EntryGradient
gradient-orientation = vertical
}
gradient EntryGradient {
area (color = red, offset = 0.0)
area (color = white, offset = 1.0)
}
gradient LoopGradient {
area (color = green, offset = 0.0)
area (color = white, offset = 1.0)
}
shape
shape EntryFigure {
ellipse {
position (x=0, y=0)
size (width=50, height=50)
style (background-color=black)
ellipse {
style (
background-color = EntryGradient
gradient-orientation = vertical
)
position (x=2, y=2)
size (width=46, height=46)
}
}
}
Shape Generator aborts with:
!ENTRY org.apache.log4j 4 0 2012-11-20 19:25:54.241
!MESSAGE org.eclipse.xtext.builder.impl.XtextBuilder - Unhandled parameter types: [org.eclipselabs.spray.styles.styles.impl.GradientRefImpl@6f70c58b]
!STACK 0
java.lang.IllegalArgumentException: Unhandled parameter types: [org.eclipselabs.spray.styles.styles.impl.GradientRefImpl@6f70c58b]
at org.eclipselabs.spray.styles.generator.StyleGenerator.createColorValue(StyleGenerator.java:979)
at org.eclipselabs.spray.shapes.generator.shapes.ShapeTypeStyleGenerator.generateStyleForElement(ShapeTypeStyleGenerator.java:41)
at org.eclipselabs.spray.shapes.generator.shapes.ShapeTypeGenerator._createElement(ShapeTypeGenerator.java:692)
at org.eclipselabs.spray.shapes.generator.shapes.ShapeTypeGenerator.createElement(ShapeTypeGenerator.java:1345)
at org.eclipselabs.spray.shapes.generator.shapes.ShapeTypeGenerator.recursiveCreation(ShapeTypeGenerator.java:215)
at org.eclipselabs.spray.shapes.generator.shapes.ShapeTypeGenerator._createElement(ShapeTypeGenerator.java:732)
at org.eclipselabs.spray.shapes.generator.shapes.ShapeTypeGenerator.createElement(ShapeTypeGenerator.java:1345)
at org.eclipselabs.spray.shapes.generator.shapes.ShapeTypeGenerator.generateCascadedElements(ShapeTypeGenerator.java:183)
at org.eclipselabs.spray.shapes.generator.GeneratorShapeDefinition.body(GeneratorShapeDefinition.java:244)
at org.eclipselabs.spray.shapes.generator.GeneratorShapeDefinition.compile(GeneratorShapeDefinition.java:75)
at org.eclipselabs.spray.shapes.generator.ShapeGenerator._generateJava(ShapeGenerator.java:73)
at org.eclipselabs.spray.shapes.generator.ShapeGenerator.generateJava(ShapeGenerator.java:114)
at org.eclipselabs.spray.shapes.generator.ShapeGenerator.doGenerate(ShapeGenerator.java:57)
at org.eclipse.xtext.builder.BuilderParticipant.handleChangedContents(BuilderParticipant.java:259)
at org.eclipselabs.spray.shapes.ui.builder.ShapeBuilderParticipant.handleChangedContents(ShapeBuilderParticipant.java:15)
at org.eclipse.xtext.builder.BuilderParticipant.build(BuilderParticipant.java:194)
at org.eclipse.xtext.builder.impl.RegistryBuilderParticipant.build(RegistryBuilderParticipant.java:60)
at org.eclipse.xtext.builder.impl.XtextBuilder.doBuild(XtextBuilder.java:161)
at org.eclipse.xtext.builder.impl.XtextBuilder.incrementalBuild(XtextBuilder.java:141)
at org.eclipse.xtext.builder.impl.XtextBuilder.build(XtextBuilder.java:91)
at org.eclipse.core.internal.events.BuildManager$2.run(BuildManager.java:728)
at org.eclipse.core.runtime.SafeRunner.run(SafeRunner.java:42)
at org.eclipse.core.internal.events.BuildManager.basicBuild(BuildManager.java:199)
at org.eclipse.core.internal.events.BuildManager.basicBuild(BuildManager.java:239)
at org.eclipse.core.internal.events.BuildManager$1.run(BuildManager.java:292)
at org.eclipse.core.runtime.SafeRunner.run(SafeRunner.java:42)
at org.eclipse.core.internal.events.BuildManager.basicBuild(BuildManager.java:295)
at org.eclipse.core.internal.events.BuildManager.basicBuildLoop(BuildManager.java:351)
at org.eclipse.core.internal.events.BuildManager.build(BuildManager.java:374)
at org.eclipse.core.internal.events.AutoBuildJob.doBuild(AutoBuildJob.java:143)
at org.eclipse.core.internal.events.AutoBuildJob.run(AutoBuildJob.java:241)
at org.eclipse.core.internal.jobs.Worker.run(Worker.java:53)
20.11.2012 20:15:42 (joswarmer):
22.11.2012 14:03:09 (joswarmer): Found the problem. Gradient as backgropund color needs to be treated differently from other colors. In the Styles DSL this is done correctly, need to do it the same way in the shapes DSL.
- stakeholder: Spray user
- keywords: Type: Defect, Priority: Medium
- status: IN_PROGRESS

## issue0207
Non compiling code for some shapes using polygons
20.11.2012 19:37:53 (de.abg.reichert.joerg): shape LWC_Valve {
polygon {
point (x=0, y=0)
point (x=120, y=60)
point (x=120, y=0)
point (x=0, y=60)
}
text {
position (x=30, y=0)
size (width=60, height=20)
id = shapeName
}
}
leads to non compiling Java code, see screenshot in appendix. Maybe an issue with polygons?
Same applies to the shapes Valve Control and Valve Manual (LWC2012 project).
20.11.2012 20:15:20 (joswarmer):
22.11.2012 13:45:58 (joswarmer): This issue was closed by revision 43dde449b4aa.
22.11.2012 13:47:20 (joswarmer): Cope paste error, Forgot to replace shape_1 with the tempalte shape name.
- stakeholder: Spray user
- keywords: Type: Defect, Priority: Medium
- status: DONE

## issue0208
The textid and compartment id in the Spray DSl should be checked
27.11.2012 11:32:22 (joswarmer): The ids of the compartments and texts from the shape DSL are not validated in the Spray DSL. This validation (and completion proposals) should be added.
27.11.2012 11:32:35 (joswarmer):
27.12.2012 19:31:14 (de.abg.reichert.joerg): Added proposals, validation as well as hyperlinking for property and compartment ids.
- stakeholder: Spray user
- keywords: Type: Task
- status: DONE

## issue0209
References to domain model ecore works only after workspace restart
01.12.2012 21:19:35 (de.abg.reichert.joerg): <b>What steps will reproduce the problem?</b>
1. Start Eclipse having Spray installed
2. create new domain model project (ecore + genmodel + generating Java out of this + export packages) OR import existing project having the characteristics from creating a new one
3. create new Spray project (configured to have reference to the domain model project)
What is the expected output?
Inside the spray DSL after having the import of the domain model package defined scoping and resolving the referenced EClass on diagram should work
What do you see instead?
The reference to the EClass cannot be resolved.
Workaround
Restart the workspace, then the EClass is resolved.
Possible causes
* the resource listener associated with the Spray scope provider do not check for newly added ecore/genmodel/Java projects
04.12.2012 20:22:38 (de.abg.reichert.joerg): This issue was closed by revision 85fb55ac4ee1.
05.12.2012 22:37:49 (Nosezeichen): I've waited for this fix :)
Im developing my ecore metamodel in iterations, e.g. if i need new EClasses or EAttributes, etc. i add them, but the Spray Project couldnt resolve these newly added EClasses.
So i always created a new Spray Project, because i didnt know how to update the Spray Project itself.
Does your fix consider this kind of development of the ecore metamodel ?
Thank you :)
06.12.2012 09:13:21 (de.abg.reichert.joerg): It is common use case to change the domain model while building the diagram
model (as you often recognize missing elements in the domain model when
defining the mapping to the diagram).
The calculation of EPackages and EClasses is cached, as this is called very
often inside the calculation of the scoping for the DSL. So it is only
recalculated when there are workspace changes (changes to projects, import
of new projects). I exclude changes to the Spray project itself as this
would lead to endless regeneration. The fix considers the case when the
change status of all projects in the workspace has not calculated yet as
well as the case when there workspace changes that do not effect resources
(e.g. the change is the creation of new project). I did not test this for
Spray installed via update site, just for Spray started in a runtime
workspace.
Also note that have to regenerate the Java sources via genmodel when you
changed the ecore model.
Joerg
- stakeholder: Spray user
- keywords: Type: Defect, Priority: Medium
- status: DONE

## issue0210
Reference to gradient in DSL is not proposed
01.12.2012 21:24:44 (de.abg.reichert.joerg): <b>What steps will reproduce the problem?</b>
1. create gradient definition in style DSL
2. create style definition in style DSL
3. trigger auto completion after &quot;background-color = &quot;
What is the expected output?
Beside the hard coded colors, JAVA and the color picker their should be the existing gradient represented by its name included in the proposal.
What do you see instead?
Only hard coded colors, JAVA and the color picker are proposed.
Workaround
Write the Gradient name manually after &quot;background-color = &quot;
Possible cause
As the scope provider works, the problem must be the proposal provider.
05.12.2012 20:03:40 (de.abg.reichert.joerg): fixed with fix of issue #218
- stakeholder: Spray user
- keywords: Type: Defect, Priority: Medium
- status: DONE

## issue0211
Propose block to bind parameters to shape definition
01.12.2012 21:27:12 (de.abg.reichert.joerg): Currently inside the Spray DSL there is not proposal shown for { after defining shape references, so it is not obvious, that it is possible to bind parameters to the shape.
02.12.2012 18:14:07 (de.abg.reichert.joerg): This issue was closed by revision eadd0daee45f.
- stakeholder: Spray user
- keywords: Type: Defect, Priority: Medium
- status: DONE

## issue0212
Wrong default style is generated when there are multiple Spray projects
01.12.2012 21:40:28 (de.abg.reichert.joerg): <b>What steps will reproduce the problem?</b>
1. Have multiple Spray projects in your workspace
2. Save a spray DSL file (associated with shapes and directly/indirectly with styles, where the style does not inherit from another style)
What is the expected output?
The generated Add feature base class should use the correct default style class.
What do you see instead?
The generated Add feature base class imports and uses the default shape class from a different (without being listed in the dependencies of the current plug-in project) Spray project.
Where it has appeared:
I had all existing example projects imported and did save the fowler.spray file, the generated StatemachineAddStateFeatureBase includes the call final ISprayStyle style = new PetrinetDefaultStyle(); instead of final ISprayStyle style = new DefaultSprayStyle();
Workaround:
Close all other Spray and restart workspace and the regenerate for the Spray DSL again.
Possible cause:
AddShapeFromDslFeature.xtend uses SprayStyleRef styleRef as global variable that is set by the call of def setAttributes(MetaClass cls, SprayStyleRef ssr), maybe this is done not only for the current project but for the hole workspace?
02.12.2012 13:40:28 (joswarmer): The styleRef is not a global variable, but as the AddShapeFromDsl is injected , it probably acts as a singleton, even over multiple projects. This is clearly not the intention. An unwated side effect from the use of injection I am afraid.
Solved it by changing the setAttributes in AddShapeFromDsl and AddConnectionFromDsl.
02.12.2012 13:41:20 (joswarmer): This issue was closed by revision 1344069fecf0.
- stakeholder: Spray user
- keywords: Type: Defect, Priority: Medium
- status: DONE

## issue0213
No or not interpreted property for gradient package name
01.12.2012 21:44:46 (de.abg.reichert.joerg): I used the following setup inside the spray.properties file:
modelFileExtension = statemachine
pluginId = org.eclipse.xtext.example.fowlerdsl.diagram
mainPackage = org.eclipse.xtext.example.fowlerdsl.diagram
diagramPackage = org.eclipse.xtext.example.fowlerdsl.diagram
featurePackage = org.eclipse.xtext.example.fowlerdsl.diagram.features
propertyPackage = org.eclipse.xtext.example.fowlerdsl.diagram.property
utilPackage = org.eclipselabs.spray.runtime.graphiti.containers
shapesPackage = org.eclipse.xtext.example.fowlerdsl.diagram.shapes
stylesPackage = org.eclipse.xtext.example.fowlerdsl.diagram.styles
gradientsPackage = org.eclipse.xtext.example.fowlerdsl.diagram.gradients
srcGenPath = src-gen
resourceGenPath = resource-gen
srcManPath = src
resourceManPath = resource
# with this, it works in the Jenkins build
projectPath = ../../../examples/fowlerdsl/org.eclipse.xtext.example.fowlerdsl.diagram
headerTimestamp = false
The gradientsPackage property is not applied when generating, so always &quot;org.eclipselabs.spray.styles.gradients&quot; is used. Either this property does not exist, is named differently or is not interpreted.
02.12.2012 09:30:43 (joswarmer):
02.12.2012 12:51:40 (joswarmer): This property was not applied, changed the generator to apply the property.
02.12.2012 12:52:38 (joswarmer): This issue was closed by revision d0fb506f96d4.
- stakeholder: Spray user
- keywords: Type: Defect, Priority: Medium
- status: DONE

## issue0214
Do not create [dsl_name].properties file anymore
01.12.2012 21:46:55 (de.abg.reichert.joerg): With the switch to spray.properties instead of [dsl_name].properties the [dsl_name].properties file should not be created when opening the Spray DSL editor.
02.12.2012 18:14:06 (de.abg.reichert.joerg): This issue was closed by revision 06bd5f9090a8.
- stakeholder: Spray user
- keywords: Type: Defect, Priority: Medium
- status: DONE

## issue0215
Discover colliding imports
01.12.2012 21:52:17 (de.abg.reichert.joerg): Giving a referenced shape the same name as used for the referenced domain model object will result in a conflicting import, where the a class with the same simple name is tried to imported from different packages. Such conflict may occur also in other situations.
class Transition {
connection Transition {
name into connectionText
// event.name into connectionText
// fromState.name into fromText
// toState.name into toText
}
The generator should discover such conflicts and should use for one class the import and for the other class full qualified access. A matter of the Spray import manager.
- stakeholder: Spray user
- keywords: Type: Defect, Priority: Low
- status: OPEN

## issue0216
Duplicate entries in generated properties view
01.12.2012 22:00:18 (de.abg.reichert.joerg): see the appended screenshot for an example. The name feature appears twice. I guess this is because the direct properties as well as the inherited properties of the current class are merged with the properties within its superclass hierarchy.
- stakeholder: Spray user
- keywords: Type: Defect, Priority: Medium
- status: OPEN

## issue0217
Better handling of text size
01.12.2012 22:16:44 (de.abg.reichert.joerg): Currently you're forced to give position, width/height and id inside a text definition otherwise you end up with a strange error message:
rule ruleCommonLayout failed predicate:
{getUnorderedGroupHelper().canLeave(grammarAccess.getCommonLayoutAccess().getUnorderedGroup_1())}?
text {
position (x=0, y=0)
size (width=20, height=10)
id = fromText
}
Width and height are dependent on the text style (font, font size, character spacing, ...)
So defining a text size has only an effect if the font size defined by the style is lower or equal to the stated size (visible when backgound-color is not set to transparent) otherwise the for style calculated size is applied and in consequence the text representation is cut of at the boundaries of the container holding the text.
01.12.2012 22:16:57 (de.abg.reichert.joerg):
02.12.2012 14:11:19 (joswarmer): The error message sounds like an internal Xtext error message. No idea what this means.
02.12.2012 14:30:30 (de.abg.reichert.joerg): Actually it seems to be an error message from the ANTLR parser combined with Xtext, here is a similar error message reported: http://www.eclipse.org/forums/index.php/t/261641/
Maybe this ugly error message is due to the nested ordered groups:
TextLayout: {TextLayout}
(
(common=CommonLayout)
& ('align' '('
(
'horizontal' '=' hAlign=HAlign ','
'vertical' '=' vAlign=VAlign
)?
')'
)?
& (layout=ShapestyleLayout)?
);
CommonLayout: {CommonLayout}
(
(
'position' '('
'x' '=' xcor=N_INT ','
'y' '=' ycor=N_INT
')'
)?
& (
'size' '('
'width' '=' width=INT ','
'height' '=' heigth=INT
')'
)
);
02.12.2012 18:39:24 (joswarmer): Unordered, and optional as well, may be optional part is also one of the cuases?
- stakeholder: Spray user
- keywords: Type: Defect, Priority: Low
- status: OPEN

## issue0218
ClassCastException StyleScopeProvider cannot be cast to XbaseScopeProvider
01.12.2012 22:18:53 (de.abg.reichert.joerg): maybe this issue is also causing issue #210?
!STACK 0
java.lang.ClassCastException: org.eclipselabs.spray.styles.scoping.StyleScopeProvider cannot be cast to org.eclipse.xtext.xbase.scoping.XbaseScopeProvider
at org.eclipse.xtext.xbase.ui.contentassist.XbaseProposalProvider.getScopeProvider(XbaseProposalProvider.java:232)
at org.eclipse.xtext.xbase.ui.contentassist.XbaseProposalProvider.lookupCrossReference(XbaseProposalProvider.java:355)
at org.eclipse.xtext.ui.editor.contentassist.AbstractJavaBasedContentProposalProvider.lookupCrossReference(AbstractJavaBasedContentProposalProvider.java:205)
at org.eclipse.xtext.xbase.ui.contentassist.XbaseProposalProvider.lookupCrossReference(XbaseProposalProvider.java:238)
at org.eclipselabs.spray.styles.ui.contentassist.AbstractStyleProposalProvider.completeGradientRef_GradientRefFromDsl(AbstractStyleProposalProvider.java:117)
at sun.reflect.NativeMethodAccessorImpl.invoke0(Native Method)
at sun.reflect.NativeMethodAccessorImpl.invoke(NativeMethodAccessorImpl.java:57)
at sun.reflect.DelegatingMethodAccessorImpl.invoke(DelegatingMethodAccessorImpl.java:43)
at java.lang.reflect.Method.invoke(Method.java:601)
at org.eclipse.xtext.util.PolymorphicDispatcher.invoke(PolymorphicDispatcher.java:291)
at org.eclipse.xtext.ui.editor.contentassist.AbstractJavaBasedContentProposalProvider.invokeMethod(AbstractJavaBasedContentProposalProvider.java:271)
at org.eclipse.xtext.ui.editor.contentassist.AbstractJavaBasedContentProposalProvider.completeAssignment(AbstractJavaBasedContentProposalProvider.java:185)
at org.eclipse.xtext.ui.editor.contentassist.AbstractContentProposalProvider$DefaultContentAssistProcessorSwitch.caseAssignment(AbstractContentProposalProvider.java:66)
at org.eclipse.xtext.ui.editor.contentassist.AbstractContentProposalProvider$DefaultContentAssistProcessorSwitch.caseAssignment(AbstractContentProposalProvider.java:1)
at org.eclipse.xtext.util.XtextSwitch.doSwitch(XtextSwitch.java:164)
at org.eclipse.xtext.util.XtextSwitch.doSwitch(XtextSwitch.java:70)
at org.eclipse.xtext.util.XtextSwitch.doSwitch(XtextSwitch.java:58)
at org.eclipse.xtext.ui.editor.contentassist.AbstractContentProposalProvider$DefaultContentAssistProcessorSwitch.accept(AbstractContentProposalProvider.java:71)
at org.eclipse.xtext.ui.editor.contentassist.AbstractContentProposalProvider.createProposals(AbstractContentProposalProvider.java:108)
at org.eclipse.xtext.ui.editor.contentassist.AbstractJavaBasedContentProposalProvider.createProposals(AbstractJavaBasedContentProposalProvider.java:246)
at org.eclipse.xtext.ui.editor.contentassist.CompletionProposalComputer.exec(CompletionProposalComputer.java:51)
at org.eclipse.xtext.ui.editor.contentassist.CompletionProposalComputer.exec(CompletionProposalComputer.java:1)
at org.eclipse.xtext.util.concurrent.AbstractReadWriteAcces.readOnly(AbstractReadWriteAcces.java:32)
at org.eclipse.xtext.ui.editor.model.XtextDocument.readOnly(XtextDocument.java:78)
at org.eclipse.xtext.ui.editor.contentassist.XtextContentAssistProcessor.computeCompletionProposals(XtextContentAssistProcessor.java:68)
at org.eclipse.xtext.ui.editor.contentassist.RepeatedContentAssistProcessor.computeCompletionProposals(RepeatedContentAssistProcessor.java:73)
at org.eclipse.jface.text.contentassist.ContentAssistant.computeCompletionProposals(ContentAssistant.java:1839)
at org.eclipse.jface.text.contentassist.CompletionProposalPopup.computeProposals(CompletionProposalPopup.java:566)
at org.eclipse.jface.text.contentassist.CompletionProposalPopup.access$16(CompletionProposalPopup.java:563)
at org.eclipse.jface.text.contentassist.CompletionProposalPopup$2.run(CompletionProposalPopup.java:498)
at org.eclipse.swt.custom.BusyIndicator.showWhile(BusyIndicator.java:70)
at org.eclipse.jface.text.contentassist.CompletionProposalPopup.showProposals(CompletionProposalPopup.java:492)
at org.eclipse.jface.text.contentassist.ContentAssistant.showPossibleCompletions(ContentAssistant.java:1665)
at org.eclipse.jface.text.source.SourceViewer.doOperation(SourceViewer.java:932)
at org.eclipse.jface.text.source.projection.ProjectionViewer.doOperation(ProjectionViewer.java:1507)
at org.eclipse.ui.texteditor.ContentAssistAction$1.run(ContentAssistAction.java:82)
at org.eclipse.swt.custom.BusyIndicator.showWhile(BusyIndicator.java:70)
at org.eclipse.ui.texteditor.ContentAssistAction.run(ContentAssistAction.java:80)
at org.eclipse.xtext.ui.editor.handler.ContentAssistHandler.execute(ContentAssistHandler.java:32)
at org.eclipse.ui.internal.handlers.HandlerProxy.execute(HandlerProxy.java:290)
at org.eclipse.ui.internal.handlers.E4HandlerProxy.execute(E4HandlerProxy.java:76)
at sun.reflect.GeneratedMethodAccessor101.invoke(Unknown Source)
at sun.reflect.DelegatingMethodAccessorImpl.invoke(DelegatingMethodAccessorImpl.java:43)
at java.lang.reflect.Method.invoke(Method.java:601)
at org.eclipse.e4.core.internal.di.MethodRequestor.execute(MethodRequestor.java:56)
at org.eclipse.e4.core.internal.di.InjectorImpl.invokeUsingClass(InjectorImpl.java:229)
at org.eclipse.e4.core.internal.di.InjectorImpl.invoke(InjectorImpl.java:210)
at org.eclipse.e4.core.contexts.ContextInjectionFactory.invoke(ContextInjectionFactory.java:131)
at org.eclipse.e4.core.commands.internal.HandlerServiceImpl.executeHandler(HandlerServiceImpl.java:171)
at org.eclipse.e4.ui.bindings.keys.KeyBindingDispatcher.executeCommand(KeyBindingDispatcher.java:276)
at org.eclipse.e4.ui.bindings.keys.KeyBindingDispatcher.press(KeyBindingDispatcher.java:494)
at org.eclipse.e4.ui.bindings.keys.KeyBindingDispatcher.processKeyEvent(KeyBindingDispatcher.java:545)
at org.eclipse.e4.ui.bindings.keys.KeyBindingDispatcher.filterKeySequenceBindings(KeyBindingDispatcher.java:366)
at org.eclipse.e4.ui.bindings.keys.KeyBindingDispatcher.access$0(KeyBindingDispatcher.java:313)
at org.eclipse.e4.ui.bindings.keys.KeyBindingDispatcher$KeyDownFilter.handleEvent(KeyBindingDispatcher.java:82)
at org.eclipse.swt.widgets.EventTable.sendEvent(EventTable.java:84)
at org.eclipse.swt.widgets.Display.filterEvent(Display.java:1262)
at org.eclipse.swt.widgets.Widget.sendEvent(Widget.java:1052)
at org.eclipse.swt.widgets.Widget.sendEvent(Widget.java:1077)
at org.eclipse.swt.widgets.Widget.sendEvent(Widget.java:1062)
at org.eclipse.swt.widgets.Widget.sendKeyEvent(Widget.java:1104)
at org.eclipse.swt.widgets.Widget.sendKeyEvent(Widget.java:1100)
at org.eclipse.swt.widgets.Widget.wmChar(Widget.java:1521)
at org.eclipse.swt.widgets.Control.WM_CHAR(Control.java:4640)
at org.eclipse.swt.widgets.Canvas.WM_CHAR(Canvas.java:345)
at org.eclipse.swt.widgets.Control.windowProc(Control.java:4528)
at org.eclipse.swt.widgets.Canvas.windowProc(Canvas.java:341)
at org.eclipse.swt.widgets.Display.windowProc(Display.java:4976)
at org.eclipse.swt.internal.win32.OS.DispatchMessageW(Native Method)
at org.eclipse.swt.internal.win32.OS.DispatchMessage(OS.java:2546)
at org.eclipse.swt.widgets.Display.readAndDispatch(Display.java:3756)
at org.eclipse.e4.ui.internal.workbench.swt.PartRenderingEngine$9.run(PartRenderingEngine.java:1029)
at org.eclipse.core.databinding.observable.Realm.runWithDefault(Realm.java:332)
at org.eclipse.e4.ui.internal.workbench.swt.PartRenderingEngine.run(PartRenderingEngine.java:923)
at org.eclipse.e4.ui.internal.workbench.E4Workbench.createAndRunUI(E4Workbench.java:86)
at org.eclipse.ui.internal.Workbench$5.run(Workbench.java:588)
at org.eclipse.core.databinding.observable.Realm.runWithDefault(Realm.java:332)
at org.eclipse.ui.internal.Workbench.createAndRunWorkbench(Workbench.java:543)
at org.eclipse.ui.PlatformUI.createAndRunWorkbench(PlatformUI.java:149)
at org.eclipse.ui.internal.ide.application.IDEApplication.start(IDEApplication.java:124)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:353)
at org.eclipse.core.runtime.adaptor.EclipseStarter.run(EclipseStarter.java:180)
at sun.reflect.NativeMethodAccessorImpl.invoke0(Native Method)
at sun.reflect.NativeMethodAccessorImpl.invoke(NativeMethodAccessorImpl.java:57)
at sun.reflect.DelegatingMethodAccessorImpl.invoke(DelegatingMethodAccessorImpl.java:43)
at java.lang.reflect.Method.invoke(Method.java:601)
at org.eclipse.equinox.launcher.Main.invokeFramework(Main.java:629)
at org.eclipse.equinox.launcher.Main.basicRun(Main.java:584)
at org.eclipse.equinox.launcher.Main.run(Main.java:1438)
at org.eclipse.equinox.launcher.Main.main(Main.java:1414)
02.12.2012 18:14:06 (de.abg.reichert.joerg): This issue was closed by revision 57f4024d7c8d.
- stakeholder: Spray user
- keywords: Type: Defect, Priority: Medium
- status: DONE

## issue0219
Browse workspace in new project wizard does not work
03.12.2012 11:24:04 (joswarmer): The browse workspace buton in the new SPray project wizard does nothing. When pressed get the following stack trace:
!ENTRY org.eclipse.ui 4 0 2012-12-03 11:20:44.495
!MESSAGE Unhandled event loop exception
!STACK 0
java.lang.NullPointerException
at org.eclipselabs.spray.xtext.ui.wizard.MetamodelSelectionComposite$BrowseResourceSelectionAdapter$1$1.visit(MetamodelSelectionComposite.java:337)
at org.eclipse.core.internal.resources.Resource$2.visit(Resource.java:126)
at org.eclipse.core.internal.resources.Resource$1.visitElement(Resource.java:85)
at org.eclipse.core.internal.watson.ElementTreeIterator.doIteration(ElementTreeIterator.java:82)
at org.eclipse.core.internal.watson.ElementTreeIterator.doIteration(ElementTreeIterator.java:86)
at org.eclipse.core.internal.watson.ElementTreeIterator.iterate(ElementTreeIterator.java:127)
at org.eclipse.core.internal.resources.Resource.accept(Resource.java:95)
at org.eclipse.core.internal.resources.Resource.accept(Resource.java:52)
at org.eclipse.core.internal.resources.Resource.accept(Resource.java:124)
at org.eclipse.core.internal.resources.Resource.accept(Resource.java:108)
at org.eclipselabs.spray.xtext.ui.wizard.MetamodelSelectionComposite$BrowseResourceSelectionAdapter$1.select(MetamodelSelectionComposite.java:327)
at org.eclipse.jface.viewers.ViewerFilter.filter(ViewerFilter.java:51)
at org.eclipse.ui.dialogs.ElementTreeSelectionDialog.evaluateIfTreeEmpty(ElementTreeSelectionDialog.java:375)
at org.eclipse.ui.dialogs.ElementTreeSelectionDialog.open(ElementTreeSelectionDialog.java:219)
at org.eclipse.emf.common.ui.dialogs.WorkspaceResourceDialog.openFileSelection(WorkspaceResourceDialog.java:123)
at org.eclipselabs.spray.xtext.ui.wizard.MetamodelSelectionComposite$BrowseResourceSelectionAdapter.widgetSelected(MetamodelSelectionComposite.java:352)
at org.eclipse.swt.widgets.TypedListener.handleEvent(TypedListener.java:248)
at org.eclipse.swt.widgets.EventTable.sendEvent(EventTable.java:84)
at org.eclipse.swt.widgets.Widget.sendEvent(Widget.java:1053)
at org.eclipse.swt.widgets.Display.runDeferredEvents(Display.java:4169)
at org.eclipse.swt.widgets.Display.readAndDispatch(Display.java:3758)
at org.eclipse.jface.window.Window.runEventLoop(Window.java:825)
at org.eclipse.jface.window.Window.open(Window.java:801)
at org.eclipse.ui.internal.actions.NewWizardShortcutAction.run(NewWizardShortcutAction.java:135)
at org.eclipse.jface.action.Action.runWithEvent(Action.java:498)
at org.eclipse.jface.action.ActionContributionItem.handleWidgetSelection(ActionContributionItem.java:584)
at org.eclipse.jface.action.ActionContributionItem.access$2(ActionContributionItem.java:501)
at org.eclipse.jface.action.ActionContributionItem$5.handleEvent(ActionContributionItem.java:411)
at org.eclipse.swt.widgets.EventTable.sendEvent(EventTable.java:84)
at org.eclipse.swt.widgets.Widget.sendEvent(Widget.java:1053)
at org.eclipse.swt.widgets.Display.runDeferredEvents(Display.java:4169)
at org.eclipse.swt.widgets.Display.readAndDispatch(Display.java:3758)
at org.eclipse.e4.ui.internal.workbench.swt.PartRenderingEngine$9.run(PartRenderingEngine.java:1022)
at org.eclipse.core.databinding.observable.Realm.runWithDefault(Realm.java:332)
at org.eclipse.e4.ui.internal.workbench.swt.PartRenderingEngine.run(PartRenderingEngine.java:916)
at org.eclipse.e4.ui.internal.workbench.E4Workbench.createAndRunUI(E4Workbench.java:86)
at org.eclipse.ui.internal.Workbench$5.run(Workbench.java:585)
at org.eclipse.core.databinding.observable.Realm.runWithDefault(Realm.java:332)
at org.eclipse.ui.internal.Workbench.createAndRunWorkbench(Workbench.java:540)
at org.eclipse.ui.PlatformUI.createAndRunWorkbench(PlatformUI.java:149)
at org.eclipse.ui.internal.ide.application.IDEApplication.start(IDEApplication.java:124)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:353)
at org.eclipse.core.runtime.adaptor.EclipseStarter.run(EclipseStarter.java:180)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.equinox.launcher.Main.invokeFramework(Main.java:629)
at org.eclipse.equinox.launcher.Main.basicRun(Main.java:584)
at org.eclipse.equinox.launcher.Main.run(Main.java:1438)
at org.eclipse.equinox.launcher.Main.main(Main.java:1414)
03.12.2012 11:35:10 (joswarmer): NPE happened when file sextantion was null, chngaed the test to accept this.
- stakeholder: Spray user
- keywords: Type: Defect, Priority: Medium
- status: DONE

## issue0220
Migrate org.eclipselabs.spray:org.eclipselabs.spray.xtext.tests
03.12.2012 17:25:56 (de.abg.reichert.joerg): The tests in org.eclipselabs.spray:org.eclipselabs.spray.xtext.tests are still based on using containers inside Spray DSL. This have to be changed to reference shapes form shape DSL files.
So the test setup have to be changed in a way that shapes and styles are resolved as valid EMF resources.
- stakeholder: Spray user
- keywords: Type: Task
- status: OPEN

## issue0221
Migrate org.eclipselabs.spray.shapes.tests
03.12.2012 17:27:52 (de.abg.reichert.joerg): Some test files have to use the new JAVA keyword, there are some strange issues with serialization:
org.junit.ComparisonFailure: expected:&lt;shape LineTest {
[line {
point (x=0, y=0)
point (x=10, y=1]0)
}
}&gt; but was:&lt;shape LineTest {
[size-min (width=0, height=0) size-max (width=0, height=0)
line {
point (x=0, y=0, curveBefore=0, curveAfter=0)
point (x=10, y=10, curveBefore=0, curveAfter=]0)
}
}&gt;
30.12.2012 10:29:01 (de.abg.reichert.joerg): fixed with commit 661cc358d7814438554f592b0eb85b252cb39fef
- stakeholder: Spray user
- keywords: Type: Task
- status: DONE

## issue0222
Review org.eclipselabs.spray:org.eclipselabs.spray.generator.graphiti.tests
03.12.2012 17:34:52 (de.abg.reichert.joerg): The tests for asserting the expected for the Spray generator are themselves generated now.
The test assertions have to be checked against the actual produced generated code at runtime to verify that there are no differences due to not resolved shapes/styles/genmodels or other influences.
This check might be done by comparing the actual generated code (to be copied inside the test project) with the code fragments to be generated as assertions (actually the generation approach has been chosen to avoid platform dependent differences in line break characters).
There also some issues with generated code assertions because of trailing empty lines inside the generated code.
When the generated test cases are verified add test case generators for the other example projects.
- stakeholder: Spray user
- keywords: Type: Task
- status: OPEN

## issue0223
Regenerate and implement test cases on platform level for example Spray projects
03.12.2012 17:39:18 (de.abg.reichert.joerg): There has been unit test case stubs pregenerated for the example one Spray project (a test class for each generated class (e.g. add feature, update feature and so on was generated). These has been removed as they were no longer valid for the now generated code.
Regenerate those test case stubs for the new generated code basis AND check if it is feasible to implement valid unit tests (maybe with some mocking) on top of them.
03.12.2012 17:39:31 (de.abg.reichert.joerg):
- stakeholder: Spray user
- keywords: Type: Task
- status: OPEN

## issue0224
Editing .shape file results in opening the generated .svg file
05.12.2012 18:06:58 (Nosezeichen): Hello,
i've got a really annoying problem when editing my shape file.
Everytime i type a single letter (without saving) the svg files in the folder &quot;shapepreviews/svg/&quot; are regenerated. This has the affect that i get a dialog for Downloading or Opening the file.
After that the Focus of my cursor isnt in the shape editor anymore and i have to click into the right place in the editor to complete my editing.
<b>What steps will reproduce the problem?</b>
1. Create Eclipse Project with your own MetaModel like described in the User-Guide
2. Create Eclipse Spray-Project using that MetaModel like described in the User-Guide
3. Edit the .shape file (typing a single letter is enough)
<b>What is the expected output? What do you see instead?</b>
Expected output:
- A Hover of the shape wich is on focus (if this feature is allready existing in the version of spray i use, see below)
- Nothing (if the hover feature isnt available in the version of spray that i use)
<b>What version of the product are you using? On what operating system?</b>
OS: Windows 7 Professional SP1 64-Bit Architecture
Eclipse: Fresh copy of eclipse-jee-juno-SR1-win32-x86_64
Runtime-JRE of Eclipse: JDK 1.7
JRE System Library of Spray and MetaModel Projects: JDK 1.5.0_22
Spray 3rdParty: https://spray.ci.cloudbees.com/job/spray-ci-targetplatform/lastSuccessfulBuild/artifact/releng/org.eclipselabs.spray.repository/target/repository/ (at the time i installed it was Build #13, i really installed the dependencies, cause i had a fresh Eclipse Juno)
Spray SDK Feature: version 0.5.0.201211192306 https://spray.ci.cloudbees.com/job/spray-assembly-build/lastSuccessfulBuild/artifact/releng/org.eclipselabs.spray.updatesite/target/repository/ (at the time i installed it was Build #97)
<b>Please provide any additional information below.</b>
In the &quot;shapepreviews&quot; folder there is a subfolder &quot;svg&quot; wich contains the shape previews as svg file, but there is no subfolder &quot;png&quot; wich should contain the shape previews as png files (as i read)
Thank you for your help
05.12.2012 20:20:08 (de.abg.reichert.joerg): When saving the shape model file, for each shape definition a SVG file is generated.
When hovering is triggered inside the Shape DSL Editor the before generated SVG file is used to generate a png file (as the Eclipse SWT Browser is not able to interpret SVG).
So by unknown causes the png is not generated in your (although I never discovered the behavior with the pop dialog). Anyway I will handle this exception by only support png file references inside the hover and in any other case no image will be linked.
06.12.2012 09:15:34 (de.abg.reichert.joerg): With the last build (https://spray.ci.cloudbees.com/job/spray-assembly-build/109/) I tried to fix it. But I am not sure if it works.
06.12.2012 19:48:11 (Nosezeichen): I tried out the build #109 (with workaround to install it, see Section "Please provide any additional information below" in this issue https://code.google.com/a/eclipselabs.org/p/spray/issues/detail?id=225 )
Problem is still the same (Download Pop-up Dialog). I dont have a folder "shapepreviews/png" only one for the svg's.
A colleague of me doesn't have this problem. he has the same Eclipse configuration as me. Maybe it is an Problem with my OS ?
06.12.2012 19:52:56 (joswarmer): I do not have the problem either, and I am using Window7, 64 bit as well. Likely it is not your OS.
06.12.2012 21:34:26 (de.abg.reichert.joerg): It could be an issue with the configured browser in Eclipse, so a different browser engine is used as usual.
Could you please post an screenshot of this download popup?
06.12.2012 22:04:58 (Nosezeichen): The Download dialoag even pops up when i open my .shape file
06.12.2012 22:12:16 (Nosezeichen): I tried to associate .svg files to a batch file wich does nothing as a workaround. thats why the type is listed as Windows-Batchdatei (Batchfile). But this didnt help either, the download dialog still asks me if i want to download or open the file.
06.12.2012 22:31:02 (de.abg.reichert.joerg): Found the place where preview.svg comes from, in ShapeOutlinePage
@Override
public void createControl(Composite parent) {
browser = new Browser(parent, SWT.NORMAL);
stateLocation = ShapeActivator.getInstance().getStateLocation().append("preview.svg");
if (!stateLocation.toFile().exists()) {
try {
FileWriter fw = new FileWriter(stateLocation.toFile());
fw.append("");
fw.flush();
} catch (IOException e) {
e.printStackTrace();
}
}
super.createControl(parent);
}
So its not a problem of the shape hover but of the outline view. Maybe it helps as a workaround to close the outline view.
06.12.2012 22:33:05 (Nosezeichen): Thank you, closing the outline view solved the problem :)
- stakeholder: Spray user
- keywords: Type: Defect, Priority: Medium
- status: DONE

## issue0225
Activator is "invalid/not found" in runtime Eclipse
06.12.2012 19:16:59 (Nosezeichen): Hello,
i've got a Problem with the latest stable build (#109) of the &quot;Spray SDK Feature&quot;.
When i try to create a graphiti diagramm with my own diagramm type in the runtime Eclipse environment, i get an exception in the development environment console that the activator for my plugin (e.g. my diagram type &quot;jsfbuilder&quot;) is invalid (or maybe not found ?).
The result is that the &quot;diagram Area&quot; shows following message &quot;Could not find diagram type provider for jsfbuilder&quot;.
<b>What steps will reproduce the problem?</b>
1. Create or import metamodel Project (in my case ecore metamodel)
2. Create Spray Project using this metamodel
3. Launch runtime Eclipse environment
4. Create new Project and in this project a new &quot;graphiti diagram&quot; with your own diagram type
<b>What is the expected output? What do you see instead?</b>
Expected Output: A Diagram Area with the Shapes and Connections of my own metamodel.
What i See: Exception in development environment console (see attachment stacktrace.txt) and in the runtime environment i see following message in the Diagram Area &quot;Could not find diagram type provider for jsfbuilder&quot;.
<b>What version of the product are you using? On what operating system?</b>
OS: Windows 7 Professional SP1 64-Bit Architecture
Eclipse: Fresh copy of eclipse-SDK-4.2.1-win32-x86_64 (Juno Classic)
Runtime-JRE of Eclipse: JDK 1.7
JRE System Library of Spray and MetaModel Projects: JDK 1.5.0_22
Spray 3rdParty: https://spray.ci.cloudbees.com/job/spray-ci-targetplatform/lastSuccessfulBuild/artifact/releng/org.eclipselabs.spray.repository/target/repository/
(at the time i installed it was Build #13, i installed the dependencies, cause i had a fresh Eclipse Juno)
Spray SDK Feature: version 0.5.0.201212052314
https://spray.ci.cloudbees.com/job/spray-assembly-build/lastSuccessfulBuild/artifact/releng/org.eclipselabs.spray.updatesite/target/repository/
(at the time i installed it was Build #109)
<b>Please provide any additional information below.</b>
I had to do a workaround to get the Build #109 installed from the update site. The update Site misses following two components of spray:
org.eclipselabs.spray.generator.common_0.5.0.201212052314.jar
org.eclipselabs.spray.tychohelpers_0.5.0.201212052314.jar
So i downloaded the missing artifacts from the CI-Build modules,
renamed them as shown above,
put them into the eclipse dropins folder,
restarted eclipse and could then install the SPRAY SDK Feature from the update-site of Build #109.
https://spray.ci.cloudbees.com/view/1.%20Eclipse%20Juno/job/spray-assembly-build/109/org.eclipselabs.spray$org.eclipselabs.spray.tychohelpers/
https://spray.ci.cloudbees.com/view/1.%20Eclipse%20Juno/job/spray-assembly-build/109/org.eclipselabs.spray$org.eclipselabs.spray.generator.common/
I really need the fixes of Build #109, thats why i tried to get it running.
06.12.2012 19:24:29 (Nosezeichen): There's also an import that cant be resolved (just after creating new Spray Project).
import org.eclipselabs.spray.runtime.containers.OwnerPropertyDeleteFeature;
in "src-gen/diagrams/JsfbuilderFeatureProviderBase.java". i commented that line out.
06.12.2012 19:33:01 (Nosezeichen): Of course i checked if the Activator.java is there. Its location is "src-gen/spray/Activator.java".
See attachment
06.12.2012 19:47:47 (joswarmer): The OwnerPropertyDeleteFeature.java is also there in the spray project and also in the jar that is built. I don't know why it cannot be found. Same for the activator.
I do see that the eclipse JDK is 1.7, while the Spray seems to be built with JDK 1.5.
Could that cause a a problem ?
06.12.2012 20:11:18 (Nosezeichen): Tried to change all the jdk settings to 1.7, still same problem with the activator.java
and the non resolvable import.
The exact message is "The import org.eclipselabs.spray.runtime.containers cannot be resolved", e.g. the package isnt found right ?
What jdk or compliance level is recommended for the Metamodel-Project (ecore) and Spray-Project ? i thougt we had to set the compliance level in the genmodel file to 5.0
will try to set jdk settings to 5.0 for metamodel and spray project
06.12.2012 20:19:20 (joswarmer): I added the generator.common project to the feature, so you do not have to install that separately. I also remove an unnecessary reference to the tychohelper, so this project is not needed anymore.
I also commented out the three test projects that were failing, so the latest build is successful again. The failure of the tests is due to the fact that they use an outdated syntax for the Spray DSL, they need work to update them.
06.12.2012 20:48:45 (Nosezeichen): Setting all the JDK stuff to 1.5 wasnt helpful too. When setting the Runtime Eclipse JDK to run with jdk 1.5, my diagramm type isnt even selectable and i get many warnings from osgi plugins not executed with jdk 1.6.
"Missing required capability Require-Capability: osgi.ee; filter="(&(osgi.ee=JavaSE)(version=1.6))"
So i changed the compliance level of my genmodel to 1.6 (i think this was the default) and all other jdk settings too.
The SDK Feature is still not installable from the snapshot repository, see attachment
06.12.2012 22:01:00 (de.abg.reichert.joerg): triggered the assembly build with Jos' changes, so hopefully build 113 should be installable again
06.12.2012 22:31:06 (Nosezeichen): Thx, the update-site works again, without the need to install missing artefacts by hand.
07.12.2012 14:33:23 (Nosezeichen): I think the Priority of this ticket should be higher, because a fundamental functionality doesnt work in the latest build.
E.g. you cant run your diagram editor in the runtime environment as mentioned before.
Im not alone with this Problem, see the attached stacktrace of my colleague (who has exact same Eclipse and JDK configuration like me).
Thank you for your help :)
07.12.2012 14:54:31 (joswarmer): Did you copy the plugin.xml file from the src-gen folder to the root folder. If I do not do that I get the same problems, but if I copy this file everything works fine.
07.12.2012 15:23:16 (Nosezeichen): Yes, i get that exceptions even when i copy the plugin.xml from sr-gen to the root of my spray project. Same thing with my colleagues Spray Project.
Has this something to do with my the non resolvable package that i mentioned above in comment 4 ?
07.12.2012 15:40:47 (Nosezeichen): I just saw in the error log view, that there are non resolved genmodels for spray internal stuff, i guess.
see attachment.
07.12.2012 15:52:36 (joswarmer): Is your spray.properties file available and does it have property definitions for all packages ? I found that the new project wizard does create an empty spray.properties file and if the generator has already run for another project the result is that the package names from the other project are used. Which mixes up path names.
The Activator is then generated using the path name from the other project, while the manifest expects it in another path.
If theer is no other project the activator is generated in a default location which is incorrect as well.
Can you check whether the activator class is in the package that the Manifest expects it?
07.12.2012 16:08:48 (joswarmer): Eef is only used by the Fowler example project. Joerg, do we deliver example projects as part of the distribution (I don't know)? It should not have any implications unless you use the fowler example. Can you check my previous remark?
07.12.2012 16:11:54 (joswarmer): This issue was closed by revision 4a24d52abcb1.
07.12.2012 16:15:12 (joswarmer): I had exactly the same problems (see comment 13) and with the latest fix, the problems are gone in my Spray runtime. Can you verify when the new build is ready ?
07.12.2012 16:22:40 (Nosezeichen): spray.properties is available but empty. How should its content look like ?
I've got also an ${MyProjectName}.properties.
In the previous version of Spray SDK Feature (Build #97) i had no spray.properties file.
see attachment for content of my jsfbuilder.properties
07.12.2012 16:29:46 (Nosezeichen): I changed the non resolvable import from "import org.eclipselabs.spray.runtime.containers.OwnerPropertyDeleteFeature;"
to "import org.eclipselabs.spray.runtime.graphiti.containers.OwnerPropertyDeleteFeature;"
now the import can be resolved.
Is this correct this way ?
07.12.2012 16:33:17 (Nosezeichen): The Manifest expects the activator in "Bundle-Activator: ba.jsfbuilder.Activator" when i understand it right. But my Activator.java is located in "ba.jsfbuilder/src-gen/spray/Activator.java"
07.12.2012 16:33:52 (joswarmer): The name of the properties file has changed to spray.properties. the <projectname>.properties is not used anymore. The wizard should create a spray.properties file, instead of the <projectname>.properties. This is what I fixed in my lst commit. The correct properties file is created by the wizard. The wizard also creates thye first spray model files, and the spray generator runs on these files during project creation. Thus immediately generating files in the wrong location.
You should copy the contents from the <project>,properties file to the spray.properties file and then generate all code again. This might solve the problems (I did not try this)
07.12.2012 16:45:11 (Nosezeichen): This helped :)
"You should copy the contents from the <project>,properties file to the spray.properties file and then generate all code again. This might solve the problems (I did not try this)"
Thank you for your fast help. I think i can work with this version of spray now to develop my spray-project :)
07.12.2012 17:16:45 (joswarmer): Good! In that case the fix is the right one. Have fun with your Spray project, and if you have anything to show, I would find it wonderful to get some pictures of your editor.
07.12.2012 21:05:56 (Nosezeichen): Im using Spray for my Bachelor Thesis. when its finished. i'll post screenshots of it. if its ok with the university i would also share the code.
I think until then we'll see us in the spray user-group.
- stakeholder: Spray user
- keywords: Type: Defect, Priority: Medium
- status: DONE

## issue0226
Add EMF SDK to Spray 3rd party update site
23.12.2012 09:58:33 (de.abg.reichert.joerg): The EMF SDK feature includes the wizard for creating an EMF GenModel. This is required to make an domain model accessible to a Spray project.
30.12.2012 14:23:06 (de.abg.reichert.joerg): EMF SDK was already included but it is not automatically installed.
As done for PDE I just updated to user documentation with a hint, that EMF Modeling Framework SDK have to be selected.
- stakeholder: Spray user
- keywords: Type: Task
- status: DONE

## issue0227
Update Spray completion templates to not include container node anymore
23.12.2012 10:11:20 (de.abg.reichert.joerg): Still proposed:
class ... {
container ( )
{
// add content here
}
behavior {
create into containmentReference palette &quot;PaletteName&quot; askFor askFor
}
}
and
class ... {
connection ( )
{
from from
to to
fromText text ( ) { &quot;&quot; }
toText text ( ) { &quot;&quot; }
connectionText text ( ) { &quot;&quot; }
}
behavior {
create into containmentReference palette &quot;PaletteName&quot; askFor askFor
}
}
28.12.2012 22:53:16 (de.abg.reichert.joerg): This issue was closed by revision a210fede9bac.
- stakeholder: Spray user
- keywords: Type: Defect, Priority: Medium
- status: DONE

## issue0228
Update project template to do not use removed container nodes
23.12.2012 10:13:22 (de.abg.reichert.joerg): When creating a new Spray project the create style, shape and spray file contains example definitions in comments that are not valid anymore:
// Add class mappings here. Refer to EClasses here. Don't forget to configure a
// dependency to the plugin defining the EMF metamodel in META-INF/MANIFEST.MF.
// It is required to have a genmodel for the metamodel. If the Ecore model lies in
// a workspace project, this project must have the Xtext nature.
//
// Example class mapping:
// class BusinessClass icon &quot;ecore/EClass.gif&quot;:
// container ( fill=yellow )
// {
// text ( ) { &quot;&lt;&lt;&quot;+eClass.name+&quot;&gt;&gt; &quot; + name};
// line ( color=black width=2)
// }
// behavior {
// // Enable create feature for this class and add it to the palette &quot;Shapes&quot;
// create into types palette &quot;Shapes&quot;;
// }
//
// Example association mapping:
// class Association icon &quot;connection16.gif&quot;
// connection ( ) {
// from source;
// to target;
// fromText &quot;source &quot; + source.name
// }
28.12.2012 22:53:15 (de.abg.reichert.joerg): This issue was closed by revision 4bfc43180e1a.
- stakeholder: Spray user
- keywords: Type: Defect, Priority: Medium
- status: DONE

## issue0229
No proposal after alias
23.12.2012 10:17:24 (de.abg.reichert.joerg): there is no ID rule proposal after class ... alias |
Check all places where STRING and ID rules are used whether there is auto completion configured.
28.12.2012 22:53:14 (de.abg.reichert.joerg): This issue was closed by revision a3c58e4e7d0d.
- stakeholder: Spray user
- keywords: Type: Defect, Priority: Medium
- status: DONE

## issue0230
Inner compartment does not fill its container
23.12.2012 12:43:18 (de.abg.reichert.joerg): Find example project attached: nassi2.zip attached.
See example2.png for current behavior.
GraphitiTestPreferencesOutline.png and Structure.txt are each showing the container structure.
See also:
http://groups.google.com/group/spray-users/browse_thread/thread/d6724f189772127e
The problem is, that there seems to be a container shape to much in the hierarchy or at least the container for the invisible rectangle should not be selectable resp. should resize with the container with the visible rectangle.
Via Juno Update Site I have installed Graphiti SDK to get the Graphiti test preferences, so can select the containers in the outline view. By this the container is also selected in the diagram and I can resize invisible as well as visible rectangles. See ResizedViaOutlineViewSelection.PNG for the result.
21.01.2013 13:26:44 (joswarmer): I traced the creation of objects and found an error in adding a sequence at the lower levels. Workling on a solution.
21.01.2013 13:27:02 (joswarmer):
21.01.2013 18:43:14 (joswarmer): The problem was that Spray assumed that references that were created inside a compartment are always of a many multiplicity. For multiplicity one things went wrong because the old domain object was removed, but the old shape remained in the diagram. Not seeing any properties of such a shape was because there was no connected business object anymore. SOlved by removing the shaes if the multiplicity is one.
21.01.2013 21:10:32 (joswarmer): This issue was closed by revision 89904bbfe874.
- stakeholder: Spray user
- keywords: Type: Defect, Priority: Medium
- status: DONE

## issue0231
Initial creation of or change in of EMF domain model project not recognized in Spray project
23.12.2012 14:32:01 (de.abg.reichert.joerg): <b>What steps will reproduce the problem?</b>
1. Create empty EMF project
2. Create ecore model file
3. Build up valid Ecore model
4. Create EMF Generator Model on top of ecore model file
5. Generate from EMF Generator Model
5. Create Spray project via wizard and select ecore package
What is the expected output?
The import and the EClass reference on the diagram node are resolved.
What do you see instead?
* at import
Multiple markers at this line - The import fmp.* cannot be resolved - The required feature 'modelType' of
'org.eclipselabs.spray.mm.spray.impl.DiagramImpl@4ab0342e{platform:/resource/
org.eclipselabs.spray.featuremodeling.feature.diagram/model/diagram.spray#/0}' must be set
* at diagram node: Couldn't resolve reference to EClass 'Project'.
Work around: Restart Eclipse
Related issue: Changing a once resolved domain model, e.g. change the name of an ECLass and regenerate - this change is not propagated to the Spray project, so in the Spray file the renamed EClass cannot be resolved - here also only restarting Eclipse helps.
23.12.2012 14:46:15 (de.abg.reichert.joerg): What works is to import an existing domain model project and Spray project at once. Then the domain model is resolved immediately.
30.12.2012 11:08:45 (de.abg.reichert.joerg): Changes not directly related to resources are discovered and handled properly now.
A change is not immediately propagated to the spray model, only when you make the spray file dirty.
- stakeholder: Spray user
- keywords: Type: Defect, Priority: Medium
- status: DONE

## issue0232
Provide quickfixes for shape and style definitions
23.12.2012 15:56:00 (de.abg.reichert.joerg): By the removal of the container definitions inside the Spray DSL it is required to define shapes before the actual mapping from domain to diagram concepts. But the normal workflow for defining a diagram editor would still start with the Spray DSL file.
Example:
import fmp.*
diagram FeatureDiagram for Project style DiagramDefaultStyle
class Feature {
shape FeatureShape --&gt; just write here the name of the not yet existing shape definition and then a quick fix is provided to create a default shape definition in separate shape file
behavior {
create into metaModel palette &quot;Nodes&quot; askFor name
}
}
Also provide quick fixes for non resolved style and gradient references.
06.01.2013 17:00:55 (de.abg.reichert.joerg): This issue was closed by revision 513df2660df0.
- stakeholder: Spray user
- keywords: Type: Enhancement
- status: DONE

## issue0233
Allow to pass constant values to referenced shape
25.12.2012 10:59:20 (de.abg.reichert.joerg): Currently it is only possible to pass values to a referenced shape in by referencing a feature of the domain model:
class ActionBlock alias Action {
shape ActionBlockShape {
actionName into action
}
behavior {
create palette &quot;Elements&quot;
}
}
shape ActionBlockShape {
stretching(horizontal=true,vertical=true)
rectangle {
position(x=0,y=0)
size(width=100,height=100)
text {
position(x=5,y=5)
size(width=90,height=90)
id = action
}
}
}
So in the example actionName must be a feature of ActionBlock.
class ActionBlock alias Action {
shape ActionBlockShape {
actionName into action
}
As workaround you can write:
class ActionBlock alias Action {
shape ActionBlockShape {
actionName into action (&quot;Constant text&quot;)
}
But you still need an existing feature of the domain model element.
What you actually want to write is:
class ActionBlock alias Action {
shape ActionBlockShape {
&quot;Constant text&quot; into action
}
Or even more constant direct in shape:
shape ActionBlockShape {
stretching(horizontal=true,vertical=true)
rectangle {
position(x=0,y=0)
size(width=100,height=100)
text {
position(x=5,y=5)
size(width=90,height=90)
id = &quot;Constant text&quot;
}
}
}
(The last version is actually a separate issue).
27.12.2012 20:47:06 (de.abg.reichert.joerg): before:
shape UniqueRuleShape {
name into uniqueRuleName ( "Rule: " + name )
reference properties into properties
}
Now it is additional possible to write
shape UniqueRuleShape {
constant "Rule" + name into uniqueRuleName
reference properties into properties
}
And with the last syntax you can leave out the feature:
shape UniqueRuleShape {
constant "Rule" into uniqueRuleName
reference properties into properties
}
We should consider to deprecate the bracket syntax so we can leave out the keyword 'constant':
shape UniqueRuleShape {
"Rule" + name into uniqueRuleName
reference properties into properties
}
09.01.2013 21:29:02 (de.abg.reichert.joerg): The constant syntax does not work as described here:
http://groups.google.com/group/spray-users/msg/3c2c7c962bbd5951
Reason is, that the EMF feature was used for generating the DirectEditingFeature. That does not work anymore when with 'constant "Rule" into uniqueRuleName' no feature is set. So as workaround constant name into uniqueRuleName ( "Rule" ) is currently only possible.
17.05.2013 16:24:44 (de.abg.reichert.joerg): This issue was closed by revision 3c9730f3a086.
- stakeholder: Spray user
- keywords: Type: Defect, Priority: Medium
- status: DONE

## issue0234
Containment element got lost
06.01.2013 18:03:20 (de.abg.reichert.joerg): see http://groups.google.com/group/spray-users/browse_thread/thread/582d6c3c4f1b87db
I created and appended a little example to reproduce this problem occurs only, if you create a new diagram, create a new E2 instances and a new E3 instances and then save the diagram. In this case only the last created instance is saved.
If you create E2, save and then create further instances all instances will be saved.
new, E21, E31, E22, E32, save =&gt; only E32 saved.
new, E21, save, E31, E22, E32, save =&gt; E21, E31, E22, E32, saved.
06.01.2013 19:51:25 (joswarmer): This issue was closed by revision 71efdff66f75.
06.01.2013 19:53:46 (joswarmer): Problem was the the ModelService.getModel() sometimes returned a new root model object instead of returning the existing one. If you look into the ecore files in the contain.zip you will see it has multiple root elements, each with one of the created E2 or E3 elements in it.
Fixed the modelservice.
- stakeholder: Spray user
- keywords: Type: Defect, Priority: Medium
- status: DONE

## issue0235
Support compartments also for connections
09.01.2013 21:37:12 (de.abg.reichert.joerg): See http://groups.google.com/group/spray-users/browse_thread/thread/8f3b10ebfcbcea29
Could be useful when connection labels should be dependent on the containment hierarchy.
- stakeholder: Spray user
- keywords: Type: Enhancement, Priority: Medium
- status: OPEN

## issue0236
Problems with properties view when using compartments
09.01.2013 21:51:10 (de.abg.reichert.joerg): See http://groups.google.com/group/spray-users/msg/9d79bf1c730f0070
Maybe I've broke something with the last check-ins.
21.01.2013 18:55:11 (joswarmer): Probably solved by solving issue 230, need to test.
15.03.2013 11:23:44 (joswarmer): As far as I can see this has been resolved by fixing issue 230.
- stakeholder: Spray user
- keywords: Type: Defect, Priority: Medium
- status: DONE

## issue0237
Make Spray working in Eclipse Kepler (4.3)
17.01.2013 23:12:08 (dowbar2000): I try to create a Spray Project from EMF Model from your tutorial.
The first issue is no source code is generated in the spray project.
Maybe should I configure some settings? The second issue is spray-file cannot resolve my model-class, it is imported to the dependency.
<b>What steps will reproduce the problem?</b>
1. Creating the EMF model
2. Generating model classes
3. Creating Spray project
I add a picture of the spray-file error and the project I have tried.
Hope you can help me further.
Thanks alot.
Greez
Dowbar
17.01.2013 23:13:45 (dowbar2000): I forgot to mention that I use the Eclipse Juno 4.3M4 Version. Hope thats not the problem.
19.01.2013 10:31:58 (de.abg.reichert.joerg): Hi dowbar,
Eclipse 4.3 M4 is actually the forth milestone of the next Eclipse relase Kepler (not Juno). The Spray plug-ins are restricted to Juno versions. I am even not able to install Spray via update site in Eclipse 4.3 M4:
Cannot complete the install because of a conflicting dependency.
Software being installed: Spray SDK Feature 0.5.0.201301172327 (org.eclipselabs.spray.feature.sdk.feature.group 0.5.0.201301172327)
Software currently installed: Eclipse SDK 4.3.0.I20121214-0730 (org.eclipse.sdk.ide 4.3.0.I20121214-0730)
Only one of the following can be installed at once:
International Components for Unicode for Java (ICU4J) 4.4.2.v20110823 (com.ibm.icu 4.4.2.v20110823)
International Components for Unicode for Java (ICU4J) 50.1.0.v20121116-2 (com.ibm.icu 50.1.0.v20121116-2)
Cannot satisfy dependency:
From: Eclipse e4 Rich Client Platform 1.1.0.v20121210-193513-9gFTdGWGGGduU3t_iBdO01nz--4 (org.eclipse.e4.rcp.feature.group 1.1.0.v20121210-193513-9gFTdGWGGGduU3t_iBdO01nz--4)
To: com.ibm.icu [50.1.0.v20121116-2]
Cannot satisfy dependency:
From: Eclipse Platform 4.3.0.v20121210-194028-9PF7VHLnG0BBkXvb-5n61JdBeLn2Lmpr5BVxLP (org.eclipse.platform.feature.group 4.3.0.v20121210-194028-9PF7VHLnG0BBkXvb-5n61JdBeLn2Lmpr5BVxLP)
To: org.eclipse.rcp.feature.group [4.3.0.v20121212-184727-7IAUA7Bs-QiyWqWVNz0_nT4qjCeP]
Cannot satisfy dependency:
From: Eclipse RCP 4.3.0.v20121212-184727-7IAUA7Bs-QiyWqWVNz0_nT4qjCeP (org.eclipse.rcp.feature.group 4.3.0.v20121212-184727-7IAUA7Bs-QiyWqWVNz0_nT4qjCeP)
To: org.eclipse.e4.rcp.feature.group [1.1.0.v20121210-193513-9gFTdGWGGGduU3t_iBdO01nz--4]
Cannot satisfy dependency:
From: Eclipse Project SDK 4.3.0.v20120906-193403-7V7p-DQ72z-z-8U8IIz0Ennw4DFBv216MQ_3m27IU_Kz0 (org.eclipse.sdk.feature.group 4.3.0.v20120906-193403-7V7p-DQ72z-z-8U8IIz0Ennw4DFBv216MQ_3m27IU_Kz0)
To: org.eclipse.platform.feature.group [4.3.0.v20121210-194028-9PF7VHLnG0BBkXvb-5n61JdBeLn2Lmpr5BVxLP]
Cannot satisfy dependency:
From: Eclipse SDK 4.3.0.I20121214-0730 (org.eclipse.sdk.ide 4.3.0.I20121214-0730)
To: org.eclipse.sdk.feature.group [4.3.0.v20120906-193403-7V7p-DQ72z-z-8U8IIz0Ennw4DFBv216MQ_3m27IU_Kz0]
Cannot satisfy dependency:
From: Xtext UI Core 2.3.1.v201208210947 (org.eclipse.xtext.ui 2.3.1.v201208210947)
To: bundle com.ibm.icu [4.0.0,5.0.0)
Cannot satisfy dependency:
From: Spray Example "One" - Language Tests 0.5.0.201301172327 (org.eclipselabs.spray.examples.one 0.5.0.201301172327)
To: bundle org.eclipse.xtext.ui [2.3.0,2.4.0)
Cannot satisfy dependency:
From: Spray SDK Feature 0.5.0.201301172327 (org.eclipselabs.spray.feature.sdk.feature.group 0.5.0.201301172327)
To: org.eclipselabs.spray.examples.one [0.5.0.201301172327]
If you really want to use Eclipse 4.3 you have to build Spray from sources and adjust the version ranges in the MANIFEST files before. But I am not sure if there breaking API changes.
I would recommand to stay with Eclipse 4.2 (Juno). We will start thinking about supporting Kepler after the next official release of Spray.
Regards,
Joerg
19.01.2013 11:28:17 (dowbar2000): Hi Joerg,
thanks for the quick answer, I tried this on Eclipse Juno now, but if I want to install the Spray SDK Feature 0.4.0.v20120319-1152 there are a lot of missing feature groups
Cannot complete the install because of a conflicting dependency.
Software being installed: Spray SDK Feature 0.4.0.v20120319-1152 (org.eclipselabs.spray.feature.sdk.feature.group 0.4.0.v20120319-1152)
Software currently installed: MWE 2 language SDK 2.3.0.v201206120758 (org.eclipse.emf.mwe2.language.sdk.feature.group 2.3.0.v201206120758)
Only one of the following can be installed at once:
Xtext Common Types 2.0.1.v201108020636 (org.eclipse.xtext.common.types 2.0.1.v201108020636)
Xtext Common Types 1.0.2.v201102150722 (org.eclipse.xtext.common.types 1.0.2.v201102150722)
Xtext Common Types 2.1.1.v201111141332 (org.eclipse.xtext.common.types 2.1.1.v201111141332)
Xtext Common Types 2.3.0.v201206120633 (org.eclipse.xtext.common.types 2.3.0.v201206120633)
Xtext Common Types 2.3.1.v201208210947 (org.eclipse.xtext.common.types 2.3.1.v201208210947)
Xtext Common Types 2.2.1.v201112130541 (org.eclipse.xtext.common.types 2.2.1.v201112130541)
Cannot satisfy dependency:
From: Modeling Workflow Engine 2 Language 2.3.0.v201206120758 (org.eclipse.emf.mwe2.language 2.3.0.v201206120758)
To: bundle org.eclipse.xtext.common.types 2.3.0
Cannot satisfy dependency:
From: MWE 2 language SDK 2.3.0.v201206120758 (org.eclipse.emf.mwe2.language.sdk.feature.group 2.3.0.v201206120758)
To: org.eclipse.emf.mwe2.language [2.3.0.v201206120758]
Cannot satisfy dependency:
From: Spray Feature 0.4.0.v20120319-1152 (org.eclipselabs.spray.feature.feature.group 0.4.0.v20120319-1152)
To: org.eclipselabs.spray.xtext [0.4.0.v20120319-1152]
Cannot satisfy dependency:
From: Spray SDK Feature 0.4.0.v20120319-1152 (org.eclipselabs.spray.feature.sdk.feature.group 0.4.0.v20120319-1152)
To: org.eclipselabs.spray.feature.feature.group [0.4.0.v20120319-1152]
Cannot satisfy dependency:
From: Spray Language Runtime 0.4.0.v20120319-1152 (org.eclipselabs.spray.xtext 0.4.0.v20120319-1152)
To: bundle org.eclipse.xtext.common.types [2.2.0,2.3.0)
I put all this update site link to the update
http://download.eclipse.org/releases/juno
http://download.itemis.com/updates/releases/2.0.0/
http://download.eclipse.org/technology/swtbot/helios/dev-build/update-site
http://xtext-utils.eclipselabs.org.codespot.com/git.distribution/releases/unittesting-0.9.x
http://update.eclemma.org
http://knittig.de/googlecode-mylyn-connector/update/
and
https://spray.ci.cloudbees.com/job/spray-ci-targetplatform/lastSuccessfulBuild/artifact/releng/org.eclipselabs.spray.repository/target/repository/
http://spray.eclipselabs.org.codespot.com/git.distribution/releases
Why can't I install it?
If I install the 0.5.0 Version the installation works but there is the same problem like the previous post. The spray project generate not all the sources and my emf generated source can be not resolve.
Greez
dowbar
19.01.2013 11:39:45 (dowbar2000): Hi,
if I install the third party library from your link and after that I install the spray feature 0.4.0
I got this:
Cannot complete the install because one or more required items could not be found.
Software being installed: Spray SDK Feature 0.4.0.v20120319-1152 (org.eclipselabs.spray.feature.sdk.feature.group 0.4.0.v20120319-1152)
Missing requirement: Spray Example "One" - Language Tests 0.4.0.v20120319-1152 (org.eclipselabs.spray.xtext.tests 0.4.0.v20120319-1152) requires 'bundle org.aopalliance 1.0.0' but it could not be found
Cannot satisfy dependency:
From: Spray SDK Feature 0.4.0.v20120319-1152 (org.eclipselabs.spray.feature.sdk.feature.group 0.4.0.v20120319-1152)
To: org.eclipselabs.spray.xtext.tests [0.4.0.v20120319-1152]
Greez
dowbar
20.01.2013 20:48:39 (de.abg.reichert.joerg): Hi dowbar,
the 0.4.0 release is for Indigo and a bit old. The last stable build should be used instead. And before installing the stable build 0.4. should be uninstalled if it was installed before. See also the user doc:
https://spray.ci.cloudbees.com/job/spray-docs-build/lastSuccessfulBuild/artifact/docs/org.eclipselabs.spray.doc.user/docs/html/SprayUserGuide.html#InstallSpray
I tested the update sites for the latest builds of Spray and 3rd party and generation works for me. Did you generate the classes out of the genmodel and did you add the dependency from Spray project to your EMF project. Also note, that the properties is now always named spray.properties (before it was named like your chosen diagram name).
Cheers,
Joerg
22.01.2013 13:44:19 (dowbar2000): Hi Joerg,
thank you for your help, now it works fine!
Greez
dowbar
10.02.2013 19:22:03 (joswarmer):
03.03.2013 17:13:19 (de.abg.reichert.joerg): Create a new branch "kepler" for preparing to move Spray to Kepler (but main development of Spray is still done on master (=Juno) resp. the corresponding feature branch).
The 3rd-party repository can be used as update site from here:
https://spray.ci.cloudbees.com/job/spray-ci-targetplatform-kepler/lastSuccessfulBuild/artifact/releng/org.eclipselabs.spray.repository/target/repository/
There are still problems with generation under Kepler, that have to be fixed, so no update site for Spray (Kepler) so far
17.04.2013 22:07:52 (de.abg.reichert.joerg):
20.05.2013 15:35:50 (de.abg.reichert.joerg):
- stakeholder: Spray user
- keywords: Type: Task, Priority: Low
- status: IN_PROGRESS

## issue0238
overridingGuiceModule.exsd not exported
24.01.2013 08:58:23 (karsten.thoms): In the plugin jar of org.eclipselabs.spray.runtime.xtext the extension point schema is missing. It must be added to build.properties
To verify, look at the resulting plugin at:
[https://spray.ci.cloudbees.com/job/spray-assembly-build/lastSuccessfulBuild/artifact/releng/org.eclipselabs.spray.updatesite/target/repository/plugins/]
24.01.2013 22:32:10 (de.abg.reichert.joerg): This issue was closed by revision 94810f93d515.
- stakeholder: Spray user
- keywords: Type: Defect, Priority: Medium
- status: DONE

## issue0239
produce diagram elements manually
07.02.2013 17:08:13 (3beinrundgrill): it would be very nice of one could invoke diagram elements like connections and businessmodels manually in order to parse a file which should be represented as a spray diagram
10.02.2013 19:21:19 (joswarmer): Hi, I am not sure what you are asking, can you elaborate?
10.02.2013 19:21:46 (joswarmer):
- stakeholder: Spray user
- keywords: Type: Enhancement, Priority: Medium
- status: OPEN

## issue0240
Spray projects in one workspace mess each other up
17.02.2013 22:30:30 (NikManolov): I updated Spray last week from here https://spray.ci.cloudbees.com/job/spray-assembly-build/lastSuccessfulBuild/artifact/releng/org.eclipselabs.spray.updatesite/target/repository/
My previous version dated back to September 2012. After I fixed some syntax problems (You really need to update the user documentation) the following thing happened.
<b>What steps will reproduce the problem?</b>
1. I have a spray project a.b.c.mydiagram based on a.b.c.mydiagram.model
2. I create a second spray project in the same workspace a.b.c.mydiagram_newSpray based on the same model
3. In the first project a.b.c.mydiagram I make some change in mydiagram.spray and code is generated again.
What is the expected output?
I expect small cosmetic changes to the source files
What do you see instead?
all files are generated under the package a.b.c.mydiagram_newSpray (still in the correct project). And ofcourse all old files from a.b.c.mydiagram are removed.
If I create yet another project with some other name, and change the first project, the naming of the third project is used.
<b>What version of the product are you using? On what operating system?</b>
I am using Eclipse Juno x64 with Graphiti 0.10 and Spray updated last Tuesday the 12th Feb. on Windows 7 Pro x64
<b>Please provide any additional information below.</b>
19.02.2013 20:31:50 (de.abg.reichert.joerg): Please note that we did some changes how configuration is loaded and applied. So configuration is now expected to be in a file named spray.properties, this file was named differently before. That spray.properties is created when creating a new Spray project. So when you open your the spray file of your old project with the Spray editor of the current version an empty spray.properties file is generated as fall back. The empty spray.properties file is causing this strange behavior. This shall be handled. As work around you have to copy the content of the old properties file into the new one.
19.02.2013 20:34:19 (de.abg.reichert.joerg):
20.05.2013 15:18:25 (de.abg.reichert.joerg): The user documentation contains now a section "migration notes" that list breaking changes, like this one:
https://spray.ci.cloudbees.com/job/spray-docs-build/lastSuccessfulBuild/artifact/docs/org.eclipselabs.spray.doc.user/docs/html/SprayUserGuide.html#Renamedpropertiesfile
So no further effort for doing some magic stuff to upgrade old Spray projects automatically.
- stakeholder: Spray user
- keywords: Type: Defect, Priority: Medium
- status: DONE

## issue0241
Fix problems with update feature for connections
03.03.2013 17:20:13 (de.abg.reichert.joerg): see http://groups.google.com/group/spray-users/browse_thread/thread/743290420ddc93cf
15.05.2013 22:11:47 (de.abg.reichert.joerg):
17.05.2013 11:35:54 (de.abg.reichert.joerg):
17.05.2013 11:42:07 (de.abg.reichert.joerg):
17.05.2013 11:43:08 (de.abg.reichert.joerg):
17.05.2013 15:08:36 (de.abg.reichert.joerg): fixed with revision http://code.google.com/a/eclipselabs.org/p/spray/source/detail?r=fbacc55673936f698e6e5569e1d58a5352e09a2b
- stakeholder: Spray user
- keywords: Type: Defect, Priority: High
- status: DONE

## issue0242
Allow resizing of compartments with non-xy-layout
03.03.2013 17:27:29 (de.abg.reichert.joerg): Resizing of compartments with vertical resp. horizontal layout is currently not supported. Only by resizing one of its contained elements the size of the compartment is changable (as it is then recalculated for the compartment). The other way round would mean that there should exist a strategy that transforms a resize request at the compartment to resize requests to its contained elements (still with respect to layout manager).
See: http://groups.google.com/group/spray-users/browse_thread/thread/743290420ddc93cf
- stakeholder: Spray user
- keywords: Type: Enhancement, Priority: Low
- status: OPEN

## issue0243
Import Package missing in generated Spray MANIFEST
22.03.2013 08:33:52 (fabio.filippelli): <b>What steps will reproduce the problem?</b>
1. Create a New Spray Project (following the instructions in the &quot;5 minute guide&quot; of the user guide.
2. Wait for generation of classes in src-gen
3. See compile error in &quot;styles&quot; package
<b>What is the expected output? What do you see instead?</b>
No compile error is expected, but there is an compile error.
This package is missing in the import packages in the MANIFEST file: org.eclipselabs.spray.styles.generator.util.GradientUtilClass.
22.03.2013 11:21:15 (fabio.filippelli): This issue was closed by revision 8999dd42d06a.
16.04.2013 22:42:43 (fabio.filippelli): This issue was closed by revision 8999dd42d06a.
- stakeholder: Spray user
- keywords: Type: Defect, Priority: High, OpSys-All
- status: DONE

## issue0244
plugin.xml just in src-gen
22.03.2013 17:39:19 (fabio.filippelli): <b>What steps will reproduce the problem?</b>
1. Create a new Spray project (following steps in the 5 minutes tutorial)
2. Wait for generation of diagram
<b>What is the expected output? What do you see instead?</b>
The plugin.xml file is generated in the project folder (at least at the first time). But the plugin.xml appears just in the src-gen folder.
24.03.2013 16:46:24 (de.abg.reichert.joerg): will be fixed in conjunction with issue #89
19.05.2013 15:52:18 (de.abg.reichert.joerg): This issue was closed by revision 6bf2795fa2f4.
- stakeholder: Spray user
- keywords: Type: Defect, Priority: Medium
- status: DONE

## issue0245
reference section in metaclass
24.03.2013 14:22:51 (fabio.filippelli): <b>What steps will reproduce the problem?</b>
1. Run Spray-Runtime
2. Import archive file in workspace
3. Open petrinet.spray
4. Try the content assist before &quot;targetTransitions&quot; or &quot;targetPlaces&quot;
<b>What is the expected output? What do you see instead?</b>
A context menu opens with a content assist.
No content assist at all shows up!
28.03.2013 17:34:00 (fabio.filippelli):
31.03.2013 13:12:14 (de.abg.reichert.joerg): This issue was closed by revision c60897a01e2b.
16.04.2013 22:42:43 (karsten.thoms): This issue was closed by revision c60897a01e2b.
- stakeholder: Spray user
- keywords: Type: Defect, Priority: Medium
- status: DONE

## issue0246
No connection shape on reference section
24.03.2013 14:26:08 (fabio.filippelli): <b>What steps will reproduce the problem?</b>
1. Run Spray-Runtime
2. Import archive file in workspace (example archive file can be found on issue 245)
3. Open petrinet.shape
4. Create a connection shape
5. Open petrinet.spray
6. Add the created connection shape after the connection keyword in the line beginning with &quot;targetTransitions&quot; or &quot;targetPlaces&quot;
<b>What is the expected output? What do you see instead?</b>
Expected: The generated &quot;AddReferenceFeature&quot; fetches the defined shape.
But, following code will generated (just a free form connection)
public PictogramElement add(final IAddContext context) {
final IAddConnectionContext addConContext = (IAddConnectionContext) context;
Place addedDomainObject = (Place) context.getNewObject();
// CONNECTION WITH POLYLINE
final Connection connection = peCreateService.createFreeFormConnection(getDiagram());
connection.setStart(addConContext.getSourceAnchor());
connection.setEnd(addConContext.getTargetAnchor());
...
24.03.2013 14:26:33 (fabio.filippelli):
28.03.2013 17:33:41 (fabio.filippelli):
09.04.2013 08:51:26 (fabio.filippelli):
- stakeholder: Spray user
- keywords: Type: Defect, Priority: Medium
- status: IN_PROGRESS

## issue0247
Compartment in Rectangle with Superclass
02.04.2013 10:37:11 (dowbar2000): Hi together,
I want to visualisate for exmaple a webpage with a lot of controls in graphiti spray. I create a ecore-model with Tab, this tab contains pages (=container) where contains a lot of widgets (Labels, Buttons, etc.).
The question is why can't I referenced a superclass (=widget) for the container to the buttons or labels. This will not showing in the Toolbar and the code-generating getting error in SprayToolBehaviorProvider (because of not generating the class).
I attach the ecore-model und spray shapes files. Can you tell me how to do this with the superclass, or should I separatly references all widgets to container like pages?
The other question is, is it the right way to visualizate if I use a class (in the image it is SketchDomainModel) who reference to all classes in ecore.
Thanks for helping.
Greez Dowbar
<b>What version of the product are you using? On what operating system?</b>
0.5.0
<b>Please provide any additional information below.</b>
Eclipse Juno 4.2.2
02.04.2013 10:45:15 (dowbar2000): Another question is, if I want to use the widget in the toolbar the "SketchDomainModel"-Class should known all the widget class in ecore, is it?
07.04.2013 15:48:59 (de.abg.reichert.joerg): Hi Dowbar,
you can actually structure your domain model this way:
SketchDomainModel
* tabs : Tab [0..*]
* pages : Page [0..*]
* widgets : Widget [0..*]
* subWidgets : Widget [0..*]
* Toolbar extends Widget
* Button extends Widget
In Spray you define the mapping this way:
diagram spray for SketchDomainModel style SprayDefaultStyle
class Tab icon "ecore/EClass.gif" {
shape TabShape {
reference pages into tabCompartment
}
behavior {
create into tabs palette "Container";
}
}
class Page icon "ecore/EClass.gif" {
shape PageShape {
reference widgets into pageCompartment
}
behavior {
create palette "Container";
}
}
class Toolbar icon "ecore/EClass.gif" {
shape ToolbarShape {
reference subWidgets into toolbarCompartment
}
behavior {
create palette "Widget";
}
}
class Button icon "ecore/EClass.gif" {
shape ButtonShape {
name into buttonID
}
behavior {
create palette "Widget";
}
}
You see, you only have to leave off the "into ..." part. Adding a button to a toolbar inside the diagram will add the button domain object to the subWidgets of the toolbar domain object as the mapping definition for Toolbar states "reference subWidgets into ...".
Best regards,
Joerg
- stakeholder: Spray user
- keywords: Type: Defect, Priority: Medium
- status: DONE

## issue0248
Styling Text
04.04.2013 10:49:54 (dowbar2000): Hello,
I created a Shape with a text and the text I want to style with transparency and setting a font-color. But no changes will do if I try it. What is the issue for this siutation.
If I setup the BackgroundColor of this Text, it works fine. Seems not all attributes of styling works.
Here my exmaple code.
shape TabShape {
stretching(horizontal=false, vertical=false)
rectangle style TabStyle {
compartment (
id = tabCompartment
layout = fixed
spacing=2
margin=2
)
position (x=0, y=20)
size (width=600, height=400)
style (background-color=RGB (192, 192, 192))
}
text{
align(horizontal=center,vertical=middle)
position(x=0, y=0)
size(width=600,height=20)
style(background-color=blue font-color=red transparency=0.1)
id=tabID
}
}
Thanks a lot for regarding.
Greez
dowbar
07.04.2013 16:01:04 (de.abg.reichert.joerg): Reproduced, only
element_2.setBackground(gaService.manageColor(diagram, new ColorConstant(192, 192, 192)));
is generated inside TabShape.java although font-color has been specified in Shape DSL file.
As workaround you can put the other style information pieces inside the TabStyle that is referenced at the rectangle. This will be then applied to the contained text, too, as the styles are applied to all contained elements, see generated TabShape.java:
ISprayStyle style_2 = new sketch.diagram.styles.TabStyle();
element_2.setStyle(style_2.getStyle(diagram));
gaService.setLocationAndSize(element_2, 0, 20, 600, 400);
SprayLayoutService.setLayoutData(shape_2, 600, 400, true);
element_2.setBackground(gaService.manageColor(diagram, new ColorConstant(192, 192, 192)));
07.04.2013 16:02:52 (de.abg.reichert.joerg): set priority to low as there is work around with using the referenced style
08.04.2013 10:51:54 (dowbar2000): Hi,
I tried with the StyleFile to style the text, but nothing is changed. Thats why I tried to change it directly in the shape-file.
I have another question, are there anyway to modified the generated ShapeFile-Class?
E.g. I want to use Images in this shape, and I modified the genareted ShapeFile programmatically. I add this part to the class.
Image backgroundImg = gaService.createImage(shape_2, SketchflowImageProvider.TAB_CALENDAR);
backgroundImg.setFilled(true);
backgroundImg.setStretchH(true);
backgroundImg.setStretchV(true);
gaService.setLocationAndSize(backgroundImg, 0, 0, 600, 420);
But each time I make changes in the Shape-File, the generated-shape-file will delete this source code part. Are there anyway to move this class like "Features" to the src folder? Or how can I add this ImagePart to SourceCode automatically by generating?
Is Spray going to support Images in the Shape-Editor?
best regards,
dowbar
11.04.2013 21:30:07 (de.abg.reichert.joerg): Do you see the style properties used for the text in the generated Java style file?
The image support is tracked in issue #121 and to support generation gap pattern also for Shape and Style classes is tracked in issue #185.
12.04.2013 12:25:50 (dowbar2000): Yes I see the style setting in the generated shape file.
It was setted in the method:
/**
* This method returns the font color for the style.
* The font color will be returned separated, because Graphiti allows just the foreground color.
* The foreground color will be used for lines and fonts at the same time.
*/
@Override
public Color getFontColor(Diagram diagram) {
IGaService gaService = Graphiti.getGaService();
return gaService.manageColor(diagram, IColorConstant.WHITE);
}
best regards,
dowbar
12.04.2013 16:40:24 (de.abg.reichert.joerg): Ok, had a look inside the Shape / Style generator: When styling text you have to provide all of
* fontName = [name]
* fontSize = [number]
* italic = [yes|no]
* bold = [yes|no]
otherwise nothing is applied.
This should be changed in a way, that when there is no value specified some default value is used instead.
12.04.2013 16:48:09 (de.abg.reichert.joerg): text {
align (horizontal=center, vertical=middle)
position (x=0, y=0)
size (width=600, height=20)
style (background-color=blue font-name="Arial" font-size=12 font-italic=no font-bold=yes)
id = tabID
}
-->
{
Style style = element_2.getStyle();
String fontName = "Arial";
int fontSize = 12;
boolean fontItalic = false;
boolean fontBold = true;
style.setFont(gaService.manageFont(diagram, fontName, fontSize, fontItalic, fontBold));
}
13.04.2013 00:21:14 (dowbar2000): Why doesn't it work if I want to make the background of the text and rectangle transparent? I only want to show the label without background in other rectangles. Is it possible? When I try this, I got this issue NullPointerException:
!ENTRY org.eclipse.graphiti.ui 4 0 2013-04-13 00:15:55.646
!MESSAGE GFCommandStack.execute(Command) java.lang.NullPointerException
!STACK 0
java.lang.NullPointerException
at org.eclipse.graphiti.services.impl.GaServiceImpl.manageColor(GaServiceImpl.java:1479)
at demo.scas.sketchflow.spray.shapes.LabelShape.getShape(LabelShape.java:82)
at demo.scas.sketchflow.spray.features.SketchflowAddLabelFeatureBase.add(SketchflowAddLabelFeatureBase.java:91)
at org.eclipse.graphiti.internal.command.AddFeatureCommandWithContext.execute(AddFeatureCommandWithContext.java:76)
at org.eclipse.graphiti.ui.internal.command.GefCommandWrapper.execute(GefCommandWrapper.java:51)
at org.eclipse.graphiti.ui.internal.editor.EmfOnGefCommand.execute(EmfOnGefCommand.java:54)
at org.eclipse.graphiti.internal.command.GFPreparableCommand2.doExecute(GFPreparableCommand2.java:37)
at org.eclipse.emf.transaction.RecordingCommand.execute(RecordingCommand.java:135)
The shape style is defined:
shape LabelShape {
rectangle style LabelStyle {
position (x=0, y=0)
size (width=60, height=25)
style(background-color=transparent)
text {
align (horizontal=center, vertical=middle)
position (x=0, y=0)
size (width=60, height=25)
style (background-color=transparent font-color=black font-name="Arial" font-size=12 font-italic=no font-bold=yes)
id = labelID
}
}
}
But the generated style code contains a line with:
Shape shape_2 = peCreateService.createShape(shape_1, false);
SprayLayoutService.setId(shape_2, "LabelShape.shape_2");
Text element_2 = gaService.createPlainText(shape_2);
ISprayStyle style_2 = style_1;
element_2.setStyle(style_2.getStyle(diagram));
gaService.setLocationAndSize(element_2, 0, 0, 60, 25);
SprayLayoutService.setLayoutData(shape_2, 60, 25, true);
element_2.setHorizontalAlignment(Orientation.ALIGNMENT_CENTER);
element_2.setVerticalAlignment(Orientation.ALIGNMENT_MIDDLE);
peService.setPropertyValue(element_2, ISprayConstants.TEXT_ID, TextIds.labelID.name());
peService.setPropertyValue(shape_2, ISprayConstants.TEXT_ID, TextIds.labelID.name());
element_2.setValue("");
element_2.setBackground(gaService.manageColor(diagram, null));
{
Style style = element_2.getStyle();
String fontName = "Arial";
int fontSize = 12;
boolean fontItalic = false;
boolean fontBold = true;
style.setFont(gaService.manageFont(diagram, fontName, fontSize, fontItalic, fontBold));
}
Is the line with "element_2.setBackground(gaService.manageColor(diagram, null))" setting the background transparent?
Thank you very much for responding.
best regards,
dowbar
13.04.2013 09:22:37 (dowbar2000): Hi,
I think you are right, when I style this text with the spray.style file it works fine.
Thank you very much for supporting.
best regard,
dowbar
20.05.2013 15:04:21 (de.abg.reichert.joerg): This issue was closed by revision eb0f4f2db0dc.
- stakeholder: Spray user
- keywords: Type: Defect, Priority: Low
- status: DONE

## issue0249
Shape preview in hover under Ubuntu is not visible
07.04.2013 21:40:48 (de.abg.reichert.joerg): Using Spray Ubuntu you cannot see the shape preview inside the hover, as the hover has got a black background under Ubuntu 12.10 and the black lines of the shapes on black background, well see the screenshot appended
17.05.2013 18:47:24 (de.abg.reichert.joerg): Should be fixed by changing the configuration of Eclipse under Ubuntu:
http://stackoverflow.com/questions/5380991/eclipse-hover-background-color-property-where
21.05.2013 20:16:09 (de.abg.reichert.joerg): Since Ubuntu 10.04 you have to install gnome-color-chooser:
https://apps.ubuntu.com/cat/applications/gnome-color-chooser/
- stakeholder: Spray user
- keywords: Type: Defect, Priority: Medium
- status: DONE

## issue0250
Provide project wizards to create example projects
07.04.2013 21:46:20 (de.abg.reichert.joerg): To make the first steps with Spray more easy for newcomers there should be project wizards to create the existing example projects (mod4j busmod, BPMN2, LWC2012, Petrinet) into the workspace (analogous to Xtext's example projects wizards for domain object and statemachine examples)
20.05.2013 15:39:25 (de.abg.reichert.joerg):
- stakeholder: Spray user
- keywords: Type: Task, Priority: Low
- status: READY

## issue0251
Provide overview picture of plug-in project structure in developer guide
07.04.2013 21:49:32 (de.abg.reichert.joerg): The Spray developer guide should include a component diagram of all plug-in projects.
- stakeholder: Spray user
- keywords: Type: Task
- status: OPEN

## issue0252
Clean up preference tree
07.04.2013 21:53:31 (de.abg.reichert.joerg): The three languages Style, Shape and Spray are currently represented as direct child entries inside the Eclipse preference page. There should be only one entry &quot;Spray&quot; that aggregates all three languages, see: http://blog.dietmar-stoll.de/2012/10/clean-eclipse-preferences-tree-with.html
- stakeholder: Spray user
- keywords: Type: Task, Priority: Low
- status: OPEN

## issue0253
Provide file wizards for creating new Style, Shape and Spray files
07.04.2013 21:58:09 (de.abg.reichert.joerg): Currently you have to use the simple file wizard and give the file the extension .style or .shape or .spray to create the corresponding artifacts. There should exist dedicated file wizards for each of that language types.
- stakeholder: Spray user
- keywords: Type: Task, Priority: Low
- status: OPEN

## issue0254
Export Spray Project
08.04.2013 11:05:30 (dowbar2000): Hi,
I create a simple Spray Project and want to export it to an plug-in to use it in Eclipse. While exporting this project I got an Error-Log
There are errors like:
13. ERROR in C:\DEV\graphiti-4.2.1\workspace\demo.sketch.spray\src-gen\demo\sketch\spray\features\SprayDirectEditTabFeatureBase.java (at line 66)
public int getEditingType() {
^^^^^^^^^^^^^^^^
The method getEditingType() of type SprayDirectEditTabFeatureBase must override a superclass method
----------
----------
14. ERROR in C:\DEV\graphiti-4.2.1\workspace\demo.sketch.spray\src-gen\demo\sketch\spray\features\SprayLayoutTabFeatureBase.java (at line 36)
public boolean canLayout(final ILayoutContext context) {
^^^^^^^^^^^^^^^^^^^^^^^^^^^^^^^^^^^^^^^
The method canLayout(ILayoutContext) of type SprayLayoutTabFeatureBase must override a superclass method
The plugin is generated, but this erros irritate me.
<b>What version of the product are you using? On what operating system?</b>
0.5.0-20130331
11.04.2013 13:23:12 (dowbar2000): I think this is not only the issue, after reading the log-file in the .metadata, I saw that I got problems with my Activator it is invalid, it is same like this issue.
https://code.google.com/a/eclipselabs.org/p/spray/issues/detail?id=225
The wizard generate the spray.properties in the model folder. So thats right.
But how can I fix it?
best regards,
dowbar
11.04.2013 21:25:19 (de.abg.reichert.joerg): Ok, I could reproduce the behavior. Reason is, that the generated plug-in manifest file uses "Bundle-RequiredExecutionEnvironment: J2SE-1.5" but the generated code uses @Overrides for methods declared in interfaces. So the MANIFEST.MF have to be changed to use "Bundle-RequiredExecutionEnvironment: JavaSE-1.6"
To be fixed by us Spray developers: The Spray project wizard should always produce a MANIFEST.MF with "Bundle-RequiredExecutionEnvironment: JavaSE-1.6"
11.04.2013 22:37:25 (dowbar2000): Thanks for the reply, when I change the execution environment to JavaSe-1.6 the error log file will not generated by exporting this plug-in, but this plug-in won't work. When I try to create my domain diagram via wizard in eclipse indigo 3.8.2, an error dialog popup an shows
The selected wizard could not be started.
Plug-in demo.scas.sketchflow.spray was unable to load class demo.scas.sketchflow.spray.internal.ExecutableExtensionFactory.
demo.scas.sketchflow.spray.internal.ExecutableExtensionFactory
Otherwise the spray editor can not read my domain files. "The Unable to create DiagramTypeProcider class" will show in the spray editor.
The upcoming log shows in the event dialog:
org.eclipse.core.runtime.CoreException: Plug-in demo.scas.sketchflow.spray was unable to load class demo.scas.sketchflow.spray.internal.ExecutableExtensionFactory.
at org.eclipse.core.internal.registry.osgi.RegistryStrategyOSGI.throwException(RegistryStrategyOSGI.java:194)
at org.eclipse.core.internal.registry.osgi.RegistryStrategyOSGI.createExecutableExtension(RegistryStrategyOSGI.java:176)
at org.eclipse.core.internal.registry.ExtensionRegistry.createExecutableExtension(ExtensionRegistry.java:905)
at org.eclipse.core.internal.registry.ConfigurationElement.createExecutableExtension(ConfigurationElement.java:243)
at org.eclipse.core.internal.registry.ConfigurationElementHandle.createExecutableExtension(ConfigurationElementHandle.java:55)
at org.eclipse.graphiti.ui.internal.platform.ExtensionManager.createDiagramTypeProvider(ExtensionManager.java:248)
at org.eclipse.graphiti.ui.editor.DiagramEditor.setInput(DiagramEditor.java:544)
at org.eclipse.graphiti.ui.editor.DiagramEditor.init(DiagramEditor.java:447)
at org.eclipse.ui.internal.EditorManager.createSite(EditorManager.java:828)
at org.eclipse.ui.internal.EditorReference.createPartHelper(EditorReference.java:647)
at org.eclipse.ui.internal.EditorReference.createPart(EditorReference.java:465)
at org.eclipse.ui.internal.WorkbenchPartReference.getPart(WorkbenchPartReference.java:595)
at org.eclipse.ui.internal.EditorReference.getEditor(EditorReference.java:289)
at org.eclipse.ui.internal.WorkbenchPage.busyOpenEditorBatched(WorkbenchPage.java:2958)
at org.eclipse.ui.internal.WorkbenchPage.busyOpenEditor(WorkbenchPage.java:2863)
at org.eclipse.ui.internal.WorkbenchPage.access$11(WorkbenchPage.java:2855)
at org.eclipse.ui.internal.WorkbenchPage$10.run(WorkbenchPage.java:2806)
at org.eclipse.swt.custom.BusyIndicator.showWhile(BusyIndicator.java:70)
at org.eclipse.ui.internal.WorkbenchPage.openEditor(WorkbenchPage.java:2802)
at org.eclipse.ui.internal.WorkbenchPage.openEditor(WorkbenchPage.java:2786)
at org.eclipse.ui.internal.WorkbenchPage.openEditor(WorkbenchPage.java:2777)
at org.eclipse.ui.ide.IDE.openEditor(IDE.java:655)
at org.eclipse.ui.ide.IDE.openEditor(IDE.java:614)
at org.eclipse.jdt.internal.ui.javaeditor.EditorUtility.openInEditor(EditorUtility.java:360)
at org.eclipse.jdt.internal.ui.javaeditor.EditorUtility.openInEditor(EditorUtility.java:167)
at org.eclipse.jdt.ui.actions.OpenAction.run(OpenAction.java:249)
at org.eclipse.jdt.ui.actions.OpenAction.run(OpenAction.java:228)
at org.eclipse.jdt.ui.actions.SelectionDispatchAction.dispatchRun(SelectionDispatchAction.java:275)
at org.eclipse.jdt.ui.actions.SelectionDispatchAction.run(SelectionDispatchAction.java:251)
at org.eclipse.jdt.internal.ui.packageview.PackageExplorerActionGroup.handleOpen(PackageExplorerActionGroup.java:376)
at org.eclipse.jdt.internal.ui.packageview.PackageExplorerPart$4.open(PackageExplorerPart.java:538)
at org.eclipse.ui.OpenAndLinkWithEditorHelper$InternalListener.open(OpenAndLinkWithEditorHelper.java:48)
at org.eclipse.jface.viewers.StructuredViewer$2.run(StructuredViewer.java:866)
at org.eclipse.core.runtime.SafeRunner.run(SafeRunner.java:42)
at org.eclipse.ui.internal.JFaceUtil$1.run(JFaceUtil.java:49)
at org.eclipse.jface.util.SafeRunnable.run(SafeRunnable.java:175)
at org.eclipse.jface.viewers.StructuredViewer.fireOpen(StructuredViewer.java:864)
at org.eclipse.jface.viewers.StructuredViewer.handleOpen(StructuredViewer.java:1152)
at org.eclipse.jface.viewers.StructuredViewer$6.handleOpen(StructuredViewer.java:1256)
at org.eclipse.jface.util.OpenStrategy.fireOpenEvent(OpenStrategy.java:275)
at org.eclipse.jface.util.OpenStrategy.access$2(OpenStrategy.java:269)
at org.eclipse.jface.util.OpenStrategy$1.handleEvent(OpenStrategy.java:309)
at org.eclipse.swt.widgets.EventTable.sendEvent(EventTable.java:84)
at org.eclipse.swt.widgets.Widget.sendEvent(Widget.java:1053)
at org.eclipse.swt.widgets.Display.runDeferredEvents(Display.java:4169)
at org.eclipse.swt.widgets.Display.readAndDispatch(Display.java:3758)
at org.eclipse.ui.internal.Workbench.runEventLoop(Workbench.java:2701)
at org.eclipse.ui.internal.Workbench.runUI(Workbench.java:2665)
at org.eclipse.ui.internal.Workbench.access$4(Workbench.java:2499)
at org.eclipse.ui.internal.Workbench$7.run(Workbench.java:679)
at org.eclipse.core.databinding.observable.Realm.runWithDefault(Realm.java:332)
at org.eclipse.ui.internal.Workbench.createAndRunWorkbench(Workbench.java:668)
at org.eclipse.ui.PlatformUI.createAndRunWorkbench(PlatformUI.java:149)
at org.eclipse.ui.internal.ide.application.IDEApplication.start(IDEApplication.java:124)
at org.eclipse.equinox.internal.app.EclipseAppHandle.run(EclipseAppHandle.java:196)
at org.eclipse.core.runtime.internal.adaptor.EclipseAppLauncher.runApplication(EclipseAppLauncher.java:110)
at org.eclipse.core.runtime.internal.adaptor.EclipseAppLauncher.start(EclipseAppLauncher.java:79)
at org.eclipse.core.runtime.adaptor.EclipseStarter.run(EclipseStarter.java:353)
at org.eclipse.core.runtime.adaptor.EclipseStarter.run(EclipseStarter.java:180)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.equinox.launcher.Main.invokeFramework(Main.java:629)
at org.eclipse.equinox.launcher.Main.basicRun(Main.java:584)
at org.eclipse.equinox.launcher.Main.run(Main.java:1438)
at org.eclipse.equinox.launcher.Main.main(Main.java:1414)
Caused by: java.lang.ClassNotFoundException: demo.scas.sketchflow.spray.internal.ExecutableExtensionFactory
at org.eclipse.osgi.internal.loader.BundleLoader.findClassInternal(BundleLoader.java:501)
at org.eclipse.osgi.internal.loader.BundleLoader.findClass(BundleLoader.java:421)
at org.eclipse.osgi.internal.loader.BundleLoader.findClass(BundleLoader.java:412)
at org.eclipse.osgi.internal.baseadaptor.DefaultClassLoader.loadClass(DefaultClassLoader.java:107)
at java.lang.ClassLoader.loadClass(Unknown Source)
at org.eclipse.osgi.internal.loader.BundleLoader.loadClass(BundleLoader.java:340)
at org.eclipse.osgi.framework.internal.core.BundleHost.loadClass(BundleHost.java:229)
at org.eclipse.osgi.framework.internal.core.AbstractBundle.loadClass(AbstractBundle.java:1212)
at org.eclipse.core.internal.registry.osgi.RegistryStrategyOSGI.createExecutableExtension(RegistryStrategyOSGI.java:174)
... 65 more
Thanks alot and best regards,
dowbar
12.04.2013 16:55:15 (de.abg.reichert.joerg): Same error message as in issue #137. Do you use the exported Spray project in Indigo? Maybe there is a version conflict: the Spray project needs Juno when it is build using the JUno update sites.
12.04.2013 23:57:12 (dowbar2000): hi,
it seems to work, but if I want to export it as RCP I got issue. In the eclipse ide I can run the spray application and when i export it I got this:
!SESSION 2013-04-12 22:22:09.949 -----------------------------------------------
eclipse.buildId=unknown
java.version=1.7.0_17
java.vendor=Oracle Corporation
BootLoader constants: OS=win32, ARCH=x86_64, WS=win32, NL=de_DE
Command-line arguments: -os win32 -ws win32 -arch x86_64 -consoleLog
!ENTRY org.eclipse.osgi 4 0 2013-04-12 22:22:11.221
!MESSAGE Startup error
!STACK 1
java.lang.IllegalArgumentException: The System Bundle's start level can not be modified.
at org.eclipse.osgi.framework.internal.core.StartLevelManager.setBundleStartLevel(StartLevelManager.java:364)
at org.eclipse.core.runtime.adaptor.EclipseStarter.installBundles(EclipseStarter.java:1050)
at org.eclipse.core.runtime.adaptor.EclipseStarter.loadBasicBundles(EclipseStarter.java:622)
at org.eclipse.core.runtime.adaptor.EclipseStarter.startup(EclipseStarter.java:277)
at org.eclipse.core.runtime.adaptor.EclipseStarter.run(EclipseStarter.java:176)
at sun.reflect.NativeMethodAccessorImpl.invoke0(Native Method)
at sun.reflect.NativeMethodAccessorImpl.invoke(Unknown Source)
at sun.reflect.DelegatingMethodAccessorImpl.invoke(Unknown Source)
at java.lang.reflect.Method.invoke(Unknown Source)
at org.eclipse.equinox.launcher.Main.invokeFramework(Main.java:629)
at org.eclipse.equinox.launcher.Main.basicRun(Main.java:584)
at org.eclipse.equinox.launcher.Main.run(Main.java:1438)
at org.eclipse.equinox.launcher.Main.main(Main.java:1414)
I hope you can help me further.
best regards,
dowbar
17.04.2013 22:05:34 (de.abg.reichert.joerg): found this:
http://www.eclipse.org/forums/index.php?t=msg&goto=51528&
- stakeholder: Spray user
- keywords: Type: Defect, Priority: Medium
- status: READY

## issue0255
Update to Xtext and Xtend 2.4.0
10.04.2013 11:38:56 (fabio.filippelli): If eclipse has Xtext and Xtend 2.4.0 then many projects can not be build.
10.04.2013 19:30:14 (de.abg.reichert.joerg): This a bit related to issue #237 where I want to investigate migration to current versions of Xtext, Xtend and Graphiti.
The problem is that the current offical Juno Eclipse update already includes the Xtext 2.4 and Xtend 2.4 release although it is not that backward compatible as one would expect from stuff that is installed by using "Check for updates". So best to uninstall the 2.4 versions of Xtext, Xtend, MWE2 and reinstall the 2.3.1 version.
When I will have managed to fix the build for the Kepler branch, I will apply the changes to the Juno branch (the current master) as well.
17.05.2013 15:09:02 (de.abg.reichert.joerg):
20.05.2013 15:35:50 (de.abg.reichert.joerg):
- stakeholder: Spray user
- keywords: Type: Task, Priority: High
- status: OPEN

## issue0256
Spray generator produce invalid method calls when referenced EMF attribute starts with "is"
12.04.2013 16:12:51 (de.abg.reichert.joerg): Hi,
I have a problem with the generated Base files in spray, because they call
a wrong method name in a special case.
When I set the name of an EAttribute in my ecore model to a name that
starts with &quot;is&quot; than a method in the emf-project will generate that starts
with &quot;isIs&quot;.
Spray calls not the method which starts with &quot;isIs&quot;, Spray try to call a
method that starts with &quot;is&quot; and not exist.
Greetings René
(originally posted here: http://groups.google.com/group/spray-users/t/342bdc2a649ddbe5)
17.04.2013 21:56:18 (de.abg.reichert.joerg): This issue was closed by revision 9d84c08a736f.
17.04.2013 22:00:35 (de.abg.reichert.joerg): added test projects, to reproduce.
Fix, that is pushed removes logic that ignores attributes that already start with "is" into logic that always adds "is". Could become a problem when genmodel is configured to generate no "isIs" methods (would be better to interpret genmodel settings though).
- stakeholder: Spray user
- keywords: Type: Defect, Priority: Medium, Component: Codegen
- status: DONE

## issue0257
Using compartment in rounded-rectangle
15.04.2013 10:57:30 (dowbar2000): Hi,
why is using the compartment in the rounded rectangle impossible?
The shape editor shows an error when I add the compartment attribute to the shape.
I got this error &quot;required (...)+ loop did not match anything at input 'compartment'&quot;
Thanks a lot.
best regards,
dowbar
17.04.2013 10:58:28 (de.abg.reichert.joerg): The Shape DSL currently only allows compartments inside rectangles and ellipses. This issue is duplicate of #182.
- stakeholder: Spray user
- keywords: Type: Defect, Priority: Medium
- status: DONE

## issue0258
Shape value to EMF model
16.04.2013 11:33:58 (dowbar2000): Hi,
are there anyway to set the shape values to my emf model. E.g. I want to set the shape size, background, foreground, styles, etc. in my model for further use.
If it isn't work, which place can I get the shape information to transfer it to my emf model?
Because I want to represent each shape in my custom viewpart with other javafx. Thats why I want to set all the style information in my emf model.
Thanks a lot.
best regards,
dowbar
17.04.2013 11:06:46 (de.abg.reichert.joerg): It always has been the idea of Spray to clearly separate domain model and diagram model, so there is no support for this use case out of the box.
You can try to add a post processing step (e.g. when saving the diagram file) where you read in the Graphiti diagram model as well as the domain model and query the diagram values you need from diagram model and set them to the domain model.
Another way could be to change the logic of your custom view parts to use both diagram model as well as domain model (as in the diagram model there is the link to the domain model element for each shape).
17.05.2013 17:07:04 (de.abg.reichert.joerg): by the way, I posted a standalone example for post processing diagram and domain model: http://groups.google.com/group/spray-dev/msg/3a6f4cb3378529a6
18.05.2013 10:52:22 (fabio.filippelli): It would be great if the generation can be triggered automatically by Spray and the user is able to configure (bind) his own generator (maybe as subclass of an abstract Generator provided by Spray with default methods).
Another great step could be, that the generator is triggered by an event on the Graphiti diagram (possible events are "onUpdate" "onSave").
It should be analysed if this data could be configured in the Spray DSL.
Possible syntax?
diagram busmod for BusinessDomainModel generate onSave BusModGenerator
- stakeholder: Spray user
- keywords: Type: Enhancement, Priority: Medium, Component: Codegen
- status: OPEN

## issue0259
Genmodel can not be found on Git projects
17.04.2013 08:10:44 (fabio.filippelli): <b>What steps will reproduce the problem?</b>
1. Checkout the example projects (e.g. petrinet) from Git
2. Build everything
3. The Spray DSL can not resolve the meta model.
What is the expected output?
The DSL resolves the metamodel, because if you create a java class the meta model can be referenced from there. Just the Spray DSL cannot.
What do you see instead?
The DSL can not resolve the meta model... in the developer runtime you see following console output:
!ENTRY org.apache.log4j 4 0 2013-04-17 08:09:57.149
!MESSAGE org.eclipselabs.spray.xtext.scoping.PackageSelector - No genmodel found for package URI http://www.eclipse.org/ocl/1.1.0/OCL. If you are running in stanalone mode make sure register the genmodel file.
org.eclipse.core.internal.resources.ResourceException: Resource '/git/spray/examples/petrinet/de.htwg.petrinet.mm/model/PetriNet.genmodel' does not exist.
Hint: If you import the domain-project by copying it (check copy project on import) then the domain model (the genmodel) can be found. But often it is necessary to share this example projects on git.
17.04.2013 10:55:35 (de.abg.reichert.joerg): Correct, the PackageSelector implementation cannot currently handle project imports from other locations only copying these into the current workspace.
The PackageSelector should be able to collect ecore and genmodels from projects imported from elsewhere, too.
17.04.2013 11:29:23 (de.abg.reichert.joerg): This issue was closed by revision b36af5cdc3eb.
- stakeholder: Spray user
- keywords: Type: Defect, Priority: High, OpSys-All, Component: Language, Usability
- status: DONE

## issue0260
Discover and colliding imports
21.04.2013 16:44:58 (de.abg.reichert.joerg): Certain names used in model will lead to name collisions in generated code (reverved keywords, naming collision due to name schemes and so on). The generator (and maybe model validator) should take care.
- stakeholder: Spray user
- keywords: Type: Defect, Priority: Medium
- status: OPEN

## issue0261
Code generator uses hard coded paths (src, src-gen) in some places
21.04.2013 16:47:19 (de.abg.reichert.joerg): In some places (mostly shape and style generator) uses hard coded &quot;src&quot; and &quot;src-gen&quot; although these paths are configurable. Code generator should be fixed to retrieve the paths from configuration.
- stakeholder: Spray user
- keywords: Type: Defect, Priority: Medium
- status: OPEN

## issue0262
Remove calls of API marked as deprecated
21.04.2013 16:49:37 (de.abg.reichert.joerg): The code generator still uses some API (Xtext, Graphiti?) that is marked now as deprecated.
- stakeholder: Spray user
- keywords: Type: Task
- status: OPEN

## issue0263
Quick fix applied to file in wrong project
21.04.2013 16:53:25 (de.abg.reichert.joerg): <b>What steps will reproduce the problem?</b>
1. Having multiple Spray projects open, with same named files (e.g. diagram.spray, diagram.shape, diagram.style)
2. Use quickfix to create not yet existing Shape or Style definition
<b>What is the expected output? What do you see instead?</b>
* expected: Shape definition is created in diagram.shape file within current project
* instead: Shape definition is created in diagram.shape file in the project listed last in the workspace
17.05.2013 18:42:26 (de.abg.reichert.joerg): This issue was closed by revision 1511b7f87725.
- stakeholder: Spray user
- keywords: Type: Defect, Priority: Medium
- status: DONE

## issue0264
Shapes and Styles generated code with smaller overridable methods
21.04.2013 16:58:59 (de.abg.reichert.joerg): With introduction of the generation gap pattern for Shapes and Styles the generated code should be modularized in smaller overridable methods.
- stakeholder: Spray user
- keywords: Type: Task
- status: OPEN

## issue0265
Change color of Shape
23.04.2013 11:49:54 (dowbar2000): When I try to change the color of the shape via popupmenu by defining an action in the spray file for many times the inner graphics algorithm is null. I can't reproduce this, it seems to be work randomly. For many times when I select the shape the custom feature recognize the inner graphic algorithm, for many time it is null.
<b>What steps will reproduce the problem?</b>
1. Create a custom feature for changing shape color
2. Select a shape at runtime
3. Runs the feature and maybe the inner graphics is null
<b>What is the expected output? What do you see instead?</b>
The color of the shape is changed
<b>What version of the product are you using? On what operating system?</b>
Spray 0.5.0 (nightly), Windows 7 - 64 Bit
And even when graphic algorihtm is null, I can get it from PictogramElement, but nothing is changed. You can see it in the attached source.
Many thanks for help.
best regards,
dowbar
- stakeholder: Spray user
- keywords: Type: Defect, Priority: Medium
- status: OPEN

## issue0266
Allow adding anchor shapes at runtime (special case of compartment)
15.05.2013 21:37:38 (de.abg.reichert.joerg): see https://groups.google.com/forum/#!topic/spray-users/gu4yGOui0LU
see http://en.wikipedia.org/wiki/Composite_structure_diagram as example
(existing uml2 ecore exists here: http://git.eclipse.org/c/uml2/org.eclipse.uml2.git/tree/plugins/org.eclipse.uml2.uml/model)
17.05.2013 17:02:32 (de.abg.reichert.joerg):
- stakeholder: Spray user
- keywords: Type: Enhancement, Priority: Medium
- status: OPEN

## issue0267
Naming-Problem on Imported and Domain-Model Classes
19.05.2013 16:11:22 (fabio.filippelli): <b>What steps will reproduce the problem?</b>
1. Create a Domain Model with a class called &quot;Function&quot; (in ecore)
2. Write the class in the Spray DSL
3. Check the classes
What is the expected output?
All classes are generated correctly and are compilable.
What do you see instead?
The DirectEditBaseClass for the Function class is not compilable, because there are following imports:
import com.google.common.base.Function;
import org.eclipse.graphiti.features.IFeatureProvider;
import org.eclipse.graphiti.features.context.IDirectEditingContext;
import org.eclipse.graphiti.mm.pictograms.PictogramElement;
import org.eclipse.graphiti.mm.algorithms.GraphicsAlgorithm;
import org.eclipse.graphiti.mm.algorithms.Text;
import org.eclipse.graphiti.services.Graphiti;
import org.eclipse.graphiti.services.IPeService;
import org.eclipselabs.spray.runtime.graphiti.features.AbstractDirectEditingFeature;
import EpkDSL.Function;
The function class name is been imported twice.
A possible solution could be, to not use the import for the DomainModel classes but always the fully qualified name.
20.05.2013 00:14:27 (fabio.filippelli):
20.05.2013 00:34:14 (fabio.filippelli): This issue was closed by revision e518f194ffa8.
20.05.2013 00:39:07 (fabio.filippelli): This issue was closed by revision e6b0de7674d2.
- stakeholder: Spray user
- keywords: Type: Defect, Priority: Medium
- status: DONE

## issue0268
New shape class name scheme not applied to inner connection references
20.05.2013 16:20:38 (de.abg.reichert.joerg): Spray DSL:
diagram FeatureDiagram for Feature style DiagramDefaultStyle
class Feature {
...
references {
^references : connection ArrowConnection
}
...
}
Shape DSL:
connection ArrowConnection {
...
}
generates:
...
import org.eclipselabs.spray.featuremodeling.diagram.shapes.ArrowConnection;
...
public abstract class FeatureDiagramAddReferenceFeatureReferencesFeatureBase extends AbstractAddConnectionFeature {
}
But it should be:
import org.eclipselabs.spray.featuremodeling.diagram.shapes.ArrowConnectionConnection;
see http://code.google.com/a/eclipselabs.org/p/spray/source/browse/#git%2Fexamples%2Ffeaturemodeling for the complete example
20.05.2013 20:16:16 (fabio.filippelli): issue was already fixed with
https://code.google.com/a/eclipselabs.org/p/spray/source/detail?r=6dfb2fa26142a57f8dcac5ea2800ccff8437e55b
- stakeholder: Spray user
- keywords: Type: Defect, Priority: Medium
- status: DONE
